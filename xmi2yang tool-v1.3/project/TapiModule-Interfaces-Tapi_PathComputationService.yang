module TapiModule-Interfaces-Tapi_PathComputationService {
    namespace "uri:onf:TapiModule-Interfaces-Tapi_PathComputationService";
    prefix TapiModule-Interfaces-Tapi_PathComputationService;
    import TapiModule-ObjectClasses {
        prefix TapiModule-ObjectClasses;
    }
    import TapiModule-TypeDefinitions {
        prefix TapiModule-TypeDefinitions;
    }
    revision 2016-06-19{}
    rpc computeP2PPath {
        input {
            list servicePort {
                uses TapiModule-ObjectClasses:Tapi_ServicePort;
                max-elements 2;
                min-elements 2;
            }
            container routingConstraint {
                uses TapiModule-TypeDefinitions:Tapi_ConnectivityConstraint;
            }
            container objectiveFunction {
                uses TapiModule-TypeDefinitions:Tapi_PathObjectiveFunction;
            }
        }
        output {
            list path {
                uses TapiModule-ObjectClasses:Tapi_Path;
                min-elements 1;
            }
        }
    }
    rpc optimizeP2PPath {
        input {
            leaf pathIdOrName {
                type string;
            }
            container routingConstraint {
                uses TapiModule-TypeDefinitions:Tapi_ConnectivityConstraint;
            }
            container optimizationConstraint {
                uses TapiModule-TypeDefinitions:Tapi_PathOptimizationConstraint;
            }
            container objectiveFunction {
                uses TapiModule-TypeDefinitions:Tapi_PathObjectiveFunction;
            }
        }
        output {
            list path {
                uses TapiModule-ObjectClasses:Tapi_Path;
                min-elements 1;
            }
        }
    }
}
