module TapiModule-Interfaces-Tapi_ConnectivityService {
    namespace "uri:onf:TapiModule-Interfaces-Tapi_ConnectivityService";
    prefix TapiModule-Interfaces-Tapi_ConnectivityService;
    import TapiModule-ObjectClasses {
        prefix TapiModule-ObjectClasses;
    }
    import TapiModule-TypeDefinitions {
        prefix TapiModule-TypeDefinitions;
    }
    revision 2016-06-19{}
    rpc getConnectionDetails {
        input {
            leaf serviceIdOrName {
                type string;
            }
            leaf connectionIdOrName {
                type string;
            }
        }
        output {
            container connection {
                uses TapiModule-ObjectClasses:Tapi_Connection;
            }
        }
    }
    rpc getConnectivityServiceList {
        output {
            list serviceList {
                uses TapiModule-ObjectClasses:Tapi_ConnectivityService;
            }
        }
    }
    rpc getConnectionEndPointDetails {
        input {
            leaf serviceIdOrName {
                type string;
            }
            leaf connectionIdOrName {
                type string;
            }
            leaf connEPIdOrName {
                type string;
            }
        }
        output {
            container connEP {
                uses TapiModule-ObjectClasses:Tapi_ConnectionEndPoint;
            }
        }
    }
    rpc getServiceEndPointDetails {
        input {
            leaf serviceEPIdOrName {
                type string;
            }
        }
        output {
            container serviceEP {
                uses TapiModule-ObjectClasses:Tapi_ServiceEndPoint;
            }
        }
    }
    rpc getConnectivityServiceDetails {
        input {
            leaf serviceIdOrName {
                type string;
            }
        }
        output {
            container service {
                uses TapiModule-ObjectClasses:Tapi_ConnectivityService;
            }
        }
    }
    rpc getServiceEndPointList {
        output {
            list serviceEPList {
                uses TapiModule-ObjectClasses:Tapi_ServiceEndPoint;
            }
        }
    }
    rpc createConnectivityService {
        input {
            list servicePort {
                uses TapiModule-ObjectClasses:Tapi_ServicePort;
                min-elements 2;
            }
            container connConstraint {
                uses TapiModule-TypeDefinitions:Tapi_ConnectivityConstraint;
            }
            container connSchedule {
                uses TapiModule-TypeDefinitions:Tapi_ScheduleInfo;
            }
        }
        output {
            container connService {
                uses TapiModule-ObjectClasses:Tapi_ConnectivityService;
            }
        }
    }
    rpc updateConnectivityService {
        input {
            leaf serviceIdOrName {
                type string;
            }
            container connConstraint {
                uses TapiModule-TypeDefinitions:Tapi_ConnectivityConstraint;
            }
            container connSchedule {
                uses TapiModule-TypeDefinitions:Tapi_ScheduleInfo;
            }
        }
        output {
            container connService {
                uses TapiModule-ObjectClasses:Tapi_ConnectivityService;
            }
        }
    }
    rpc deleteConnectivityService {
        input {
            leaf serviceIdOrName {
                type string;
            }
        }
        output {
            container connService {
                uses TapiModule-ObjectClasses:Tapi_ConnectivityService;
            }
        }
    }
}
