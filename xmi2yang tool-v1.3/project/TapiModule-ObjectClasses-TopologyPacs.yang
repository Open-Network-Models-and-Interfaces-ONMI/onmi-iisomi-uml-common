module TapiModule-ObjectClasses-TopologyPacs {
    namespace "uri:onf:TapiModule-ObjectClasses-TopologyPacs";
    prefix TapiModule-ObjectClasses-TopologyPacs;
    import TapiModule-TypeDefinitions {
        prefix TapiModule-TypeDefinitions;
    }
    import TapiModule-ObjectClasses {
        prefix TapiModule-ObjectClasses;
    }
    revision 2016-06-19{}
    grouping Tapi_TransferCostPac {
        description "The cost characteristics of a TopologicalEntity not necessarily correlated to the cost of the underlying physical realization. 
            They may be quite specific to the individual TopologicalEntity e.g. opportunity cost. Relates to layer capacity
            There may be many perspectives from which cost may be considered  for a particular TopologicalEntity and hence many specific costs and potentially cost algorithms. 
            Using an entity will incur a cost. ";
        list costCharacteristicList {
            description "The list of costs where each cost relates to some aspect of the TopologicalEntity.";
            uses TapiModule-TypeDefinitions:Tapi_CostCharacteristic;
            min-elements 1;
        }
    }
    grouping Tapi_RiskParameterPac {
        description "The risk characteristics of a TopologicalEntity come directly from the underlying physical realization. 
            The risk characteristics propagate from the physical realization to the client and from the server layer to the client layer, this propagation may be modified by protection.
            A TopologicalEntity may suffer degradation or failure as a result of a problem in a part of the underlying realization.
            The realization can be partitioned into segments which have some relevant common failure modes.
            There is a risk of failure/degradation of each segment of the underlying realization.
            Each segment is a part of a larger physical/geographical unit that behaves as one with respect to failure (i.e. a failure will have a high probability of impacting the whole unit (e.g. all cables in the same duct).
            Disruptions to that larger physical/geographical unit will impact (cause failure/errors to) all TopologicalEntities that use any part of that larger physical/geographical entity.
            Any TopologicalEntity that uses any part of that larger physical/geographical unit will suffer impact and hence each TopologicalEntity shares risk.
            The identifier of each physical/geographical unit that is involved in the realization of each segment of a Topological entity can be listed in the RiskParameter_Pac of that TopologicalEntity.
            A segment has one or more risk characteristic.
            Shared risk between two TopologicalEntities compromises the integrity of any solution that use one of those TopologicalEntity as a backup for the other.
            Where two TopologicalEntities have a common risk characteristic they have an elevated probability of failing simultaneously compared to two TopologicalEntities that do not share risk characteristics.";
        list riskCharacteristicList {
            description "A list of risk characteristics for consideration in an analysis of shared risk. Each element of the list represents a specific risk consideration.";
            uses TapiModule-TypeDefinitions:Tapi_RiskCharacteristic;
            min-elements 1;
        }
    }
    grouping Tapi_LayerProtocolTransitionPac {
        description "Relevant for a Link that is formed by abstracting one or more LTPs (in a stack) to focus on the flow and deemphasize the protocol transformation. 
            This abstraction is relevant when considering multi-layer routing. 
            The layer protocols of the LTP and the order of their application to the signal is still relevant and need to be accounted for. This is derived from the LTP spec details.
            This Pac provides the relevant abstractions of the LTPs and provides the necessary association to the LTPs involved.
            Links that included details in this Pac are often referred to as Transitional Links.";
        leaf-list transitionedLayerProtocolName {
            description "Provides the ordered structure of layer protocol transitions encapsulated in the TopologicalEntity. The ordering relates to the LinkPort role.";
            type string;
            min-elements 1;
        }
        leaf-list _nodeEdgePoint {
            description "Lists the LTPs that define the layer protocol transition of the transitional link.";
            type leafref {
                path '/TapiModule-ObjectClasses:Tapi_Topology/_node/_ownedNodeEdgePoint/uuid';
            }
            min-elements 1;
        }
    }
    grouping Tapi_TransferTimingPac {
        description "A TopologicalEntity will suffer effects from the underlying physical realization related to the timing of the information passed by the TopologicalEntity.";
        leaf fixedLatencyCharacteristic {
            type string;
            description "A TopologicalEntity suffers delay caused by the realization of the servers (e.g. distance related; FEC encoding etc.) along with some client specific processing. This is the total average latency effect of the TopologicalEntity";
        }
        leaf jitterCharacteristic {
            type string;
            description "High frequency deviation from true periodicity of a signal and therefore a small high rate of change of transfer latency.
                Applies to TDM systems (and not packet).";
        }
        leaf wanderCharacteristic {
            type string;
            description "Low frequency deviation from true periodicity of a signal and therefore a small low rate of change of transfer latency.
                Applies to TDM systems (and not packet).";
        }
        leaf-list queuingLatency {
            description "The effect on the latency of a queuing process. This only has significant effect for packet based systems and has a complex characteristic.";
            type string;
        }
    }
    grouping Tapi_TransferIntegrityPac {
        description "Transfer intergrity characteristic covers expected/specified/acceptable characteristic of degradation of the transfered signal.
            It includes all aspects of possible degradation of signal content as well as any damage of any form to the total TopologicalEntity and to the carried signals.
            Note that the statement is of total impact to the TopologicalEntity so any partial usage of the TopologicalEntity (e.g. a signal that does not use full capacity) will only suffer its portion of the impact.";
        leaf errorCharacteristic {
            type string;
            description "Describes the degree to which the signal propagated can be errored. 
                Applies to TDM systems as the errored signal will be propagated and not packet as errored packets will be discarded.";
        }
        leaf lossCharacteristic {
            type string;
            description "Describes the acceptable characteristic of lost packets where loss may result from discard due to errors or overflow.
                Applies to packet systems and not TDM (as for TDM errored signals are propagated unless grossly errored and overflow/underflow turns into timing slips).";
        }
        leaf repeatDeliveryCharacteristic {
            type string;
            description "Primarily applies to packet systems where a packet may be delivered more than once (in fault recovery for example). 
                It can also apply to TDM where several frames may be received twice due to switching in a system with a large differential propagation delay.";
        }
        leaf deliveryOrderCharacteristic {
            type string;
            description "Describes the degree to which packets will be delivered out of sequence.
                Does not apply to TDM as the TDM protocols maintain strict order.";
        }
        leaf unavailableTimeCharacteristic {
            type string;
            description "Describes the duration for which there may be no valid signal propagated.";
        }
        leaf serverIntegrityProcessCharacteristic {
            type string;
            description "Describes the effect of any server integrity enhancement process on the characteristics of the TopologicalEntity.";
        }
    }
    grouping Tapi_TransferCapacityPac {
        description "The TopologicalEntity derives capacity from the underlying realization. 
            A TopologicalEntity may be an abstraction and virtualization of a subset of the underlying capability offered in a view or may be directly reflecting the underlying realization.
            A TopologicalEntity may be directly used in the view or may be assigned to another view for use.
            The clients supported by a multi-layer TopologicalEntity may interact such that the resources used by one client may impact those available to another. This is derived from the LTP spec details.
            Represents the capacity available to user (client) along with client interaction and usage. 
            A TopologicalEntity may reflect one or more client protocols and one or more members for each profile.";
        container totalPotentialCapacity {
            description "An optimistic view of the capacity of the TopologicalEntity assuming that any shared capacity is available to be taken.";
            uses TapiModule-TypeDefinitions:Tapi_Capacity;
        }
        container availableCapacity {
            description "Capacity available to be assigned.";
            uses TapiModule-TypeDefinitions:Tapi_Capacity;
        }
        list capacityAssignedToUserView {
            description "Capacity already assigned";
            uses TapiModule-TypeDefinitions:Tapi_Capacity;
        }
        leaf capacityInteractionAlgorithm {
            type string;
            description "A reference to an algorithm that describes how various chunks of allocated capacity interact (e.g. when shared)";
        }
    }
    grouping Tapi_ValidationPac {
        description "Validation covers the various adjacenct discovery and reachability verification protocols. Also may cover Information source and degree of integrity.";
        list validationMechanism {
            description "Provides details of the specific validation mechanism(s) used to confirm the presence of an intended topologicalEntity.";
            uses TapiModule-TypeDefinitions:Tapi_ValidationMechanism;
            min-elements 1;
        }
    }
}
