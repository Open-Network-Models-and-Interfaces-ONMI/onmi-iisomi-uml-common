module TapiModule-ObjectClasses {
    namespace "uri:onf:TapiModule-ObjectClasses";
    prefix TapiModule-ObjectClasses;
    import TapiModule-TypeDefinitions {
        prefix TapiModule-TypeDefinitions;
    }
    import TapiModule-ObjectClasses-TopologyPacs {
        prefix TapiModule-ObjectClasses-TopologyPacs;
    }
    revision 2016-06-19{}
    list Tapi_Topology {
        key 'uuid';
        uses Tapi_Topology;
    }
    grouping Tapi_Topology {
        description "The ForwardingDomain (FD) object class models the “ForwardingDomain” topological component which is used to effect forwarding of transport characteristic information and offers the potential to enable forwarding. 
            At the lowest level of recursion, an FD (within a network element (NE)) represents a switch matrix (i.e., a fabric). Note that an NE can encompass multiple switch matrices (FDs). ";
        list _node {
            key 'uuid';
            uses Tapi_Node;
        }
        list _link {
            key 'uuid';
            uses Tapi_Link;
        }
        leaf uuid {
            type TapiModule-TypeDefinitions:Tapi_UniversalId;
            description "UUID: An identifier that is universally unique
                (consider in the context of Identifier: A property of an entity/role with a value that is unique within an identifier space, where the identifier space is itself globally unique, and immutable. An identifier carries no semantics with respect to the purpose or state of the entity)";
        }
        list name {
            description "List of names. A property of an entity with a value that is unique in some namespace but may change during the life of the entity. A name carries no semantics with respect to the purpose of the entity.";
            uses TapiModule-TypeDefinitions:Tapi_NameAndValue;
            min-elements 1;
        }
        list label {
            description "List of labels.A property of an entity with a value that is not expected to be unique and is allowed to change. A label carries no semantics with respect to the purpose of the entity and has no effect on the entity behavior or state.";
            uses TapiModule-TypeDefinitions:Tapi_NameAndValue;
        }
        list extension {
            description "List of simple name-value extentions. Extension provides an opportunity to define properties not declared in the class that extend the class enabling a realization with simple ad-hoc extension of standard classes to be conformant.";
            uses TapiModule-TypeDefinitions:Tapi_NameAndValue;
        }
        leaf-list layerProtocolName {
            type TapiModule-TypeDefinitions:Tapi_LayerProtocolName;
            min-elements 1;
        }
    }
    container Tapi_Context {
        description "The Network Control Domain (NCD) object class represents the scope of control that a particular SDN controller has with respect to a particular network, (i.e., encompassing a designated set of interconnected (virtual) network elements).";
        leaf _topology {
            type leafref {
                path '/Tapi_Topology/uuid';
            }
        }
        leaf uuid {
            type TapiModule-TypeDefinitions:Tapi_UniversalId;
            description "UUID: An identifier that is universally unique
                (consider in the context of Identifier: A property of an entity/role with a value that is unique within an identifier space, where the identifier space is itself globally unique, and immutable. An identifier carries no semantics with respect to the purpose or state of the entity)";
        }
        list name {
            description "List of names. A property of an entity with a value that is unique in some namespace but may change during the life of the entity. A name carries no semantics with respect to the purpose of the entity.";
            uses TapiModule-TypeDefinitions:Tapi_NameAndValue;
            min-elements 1;
        }
        list label {
            description "List of labels.A property of an entity with a value that is not expected to be unique and is allowed to change. A label carries no semantics with respect to the purpose of the entity and has no effect on the entity behavior or state.";
            uses TapiModule-TypeDefinitions:Tapi_NameAndValue;
        }
        list extension {
            description "List of simple name-value extentions. Extension provides an opportunity to define properties not declared in the class that extend the class enabling a realization with simple ad-hoc extension of standard classes to be conformant.";
            uses TapiModule-TypeDefinitions:Tapi_NameAndValue;
        }
    }
    grouping Tapi_Node {
        description "The ForwardingDomain (FD) object class models the “ForwardingDomain” topological component which is used to effect forwarding of transport characteristic information and offers the potential to enable forwarding. 
            At the lowest level of recursion, an FD (within a network element (NE)) represents a switch matrix (i.e., a fabric). Note that an NE can encompass multiple switch matrices (FDs). ";
        list _ownedNodeEdgePoint {
            key 'uuid';
            uses Tapi_NodeEdgePoint;
        }
        leaf-list _aggregatedNodeEdgePoint {
            type leafref {
                path '/Tapi_Topology/_node/_ownedNodeEdgePoint/uuid';
            }
        }
        leaf _encapTopology {
            type leafref {
                path '/Tapi_Topology/uuid';
            }
        }
        leaf uuid {
            type TapiModule-TypeDefinitions:Tapi_UniversalId;
            description "UUID: An identifier that is universally unique
                (consider in the context of Identifier: A property of an entity/role with a value that is unique within an identifier space, where the identifier space is itself globally unique, and immutable. An identifier carries no semantics with respect to the purpose or state of the entity)";
        }
        list name {
            description "List of names. A property of an entity with a value that is unique in some namespace but may change during the life of the entity. A name carries no semantics with respect to the purpose of the entity.";
            uses TapiModule-TypeDefinitions:Tapi_NameAndValue;
            min-elements 1;
        }
        list label {
            description "List of labels.A property of an entity with a value that is not expected to be unique and is allowed to change. A label carries no semantics with respect to the purpose of the entity and has no effect on the entity behavior or state.";
            uses TapiModule-TypeDefinitions:Tapi_NameAndValue;
        }
        list extension {
            description "List of simple name-value extentions. Extension provides an opportunity to define properties not declared in the class that extend the class enabling a realization with simple ad-hoc extension of standard classes to be conformant.";
            uses TapiModule-TypeDefinitions:Tapi_NameAndValue;
        }
        leaf-list layerProtocolName {
            type TapiModule-TypeDefinitions:Tapi_LayerProtocolName;
            min-elements 1;
        }
        leaf administrativeState {
            type TapiModule-TypeDefinitions:Tapi_AdministrativeState;
        }
        leaf operationalState {
            type TapiModule-TypeDefinitions:Tapi_OperationalState;
        }
        leaf lifecycleState {
            type TapiModule-TypeDefinitions:Tapi_LifecycleState;
        }
        leaf _transferCapacity {
            type leafref {
                path '/TapiModule-ObjectClasses-TopologyPacs:Tapi_TransferCapacityPac/';
            }
        }
        leaf _transferCost {
            type leafref {
                path '/TapiModule-ObjectClasses-TopologyPacs:Tapi_TransferCostPac/';
            }
        }
        leaf _transferTiming {
            type leafref {
                path '/TapiModule-ObjectClasses-TopologyPacs:Tapi_TransferTimingPac/';
            }
        }
        leaf _transferIntegrity {
            type leafref {
                path '/TapiModule-ObjectClasses-TopologyPacs:Tapi_TransferIntegrityPac/';
            }
        }
    }
    grouping Tapi_Link {
        description "The Link object class models effective adjacency between two or more ForwardingDomains (FD). ";
        list _linkPort {
            key 'localId';
            uses Tapi_LinkPort;
            min-elements 2;
        }
        leaf-list _node {
            type leafref {
                path '/Tapi_Topology/_node/uuid';
            }
            min-elements 2;
        }
        leaf uuid {
            type TapiModule-TypeDefinitions:Tapi_UniversalId;
            description "UUID: An identifier that is universally unique
                (consider in the context of Identifier: A property of an entity/role with a value that is unique within an identifier space, where the identifier space is itself globally unique, and immutable. An identifier carries no semantics with respect to the purpose or state of the entity)";
        }
        list name {
            description "List of names. A property of an entity with a value that is unique in some namespace but may change during the life of the entity. A name carries no semantics with respect to the purpose of the entity.";
            uses TapiModule-TypeDefinitions:Tapi_NameAndValue;
            min-elements 1;
        }
        list label {
            description "List of labels.A property of an entity with a value that is not expected to be unique and is allowed to change. A label carries no semantics with respect to the purpose of the entity and has no effect on the entity behavior or state.";
            uses TapiModule-TypeDefinitions:Tapi_NameAndValue;
        }
        list extension {
            description "List of simple name-value extentions. Extension provides an opportunity to define properties not declared in the class that extend the class enabling a realization with simple ad-hoc extension of standard classes to be conformant.";
            uses TapiModule-TypeDefinitions:Tapi_NameAndValue;
        }
        leaf-list layerProtocolName {
            type TapiModule-TypeDefinitions:Tapi_LayerProtocolName;
            min-elements 1;
        }
        leaf direction {
            type TapiModule-TypeDefinitions:Tapi_ForwardingDirection;
            description "The directionality of the Link. 
                Is applicable to simple Links where all LinkEnds are BIDIRECTIONAL (the Link will be BIDIRECTIONAL) or UNIDIRECTIONAL (the Link will be UNIDIRECTIONAL). 
                Is not present in more complex cases.";
        }
        leaf administrativeState {
            type TapiModule-TypeDefinitions:Tapi_AdministrativeState;
        }
        leaf operationalState {
            type TapiModule-TypeDefinitions:Tapi_OperationalState;
        }
        leaf lifecycleState {
            type TapiModule-TypeDefinitions:Tapi_LifecycleState;
        }
        leaf _transferCapacity {
            type leafref {
                path '/TapiModule-ObjectClasses-TopologyPacs:Tapi_TransferCapacityPac/';
            }
        }
        leaf _transferCost {
            type leafref {
                path '/TapiModule-ObjectClasses-TopologyPacs:Tapi_TransferCostPac/';
            }
        }
        leaf _transferTiming {
            type leafref {
                path '/TapiModule-ObjectClasses-TopologyPacs:Tapi_TransferTimingPac/';
            }
        }
        leaf _transferIntegrity {
            type leafref {
                path '/TapiModule-ObjectClasses-TopologyPacs:Tapi_TransferIntegrityPac/';
            }
        }
        leaf _risk {
            type leafref {
                path '/TapiModule-ObjectClasses-TopologyPacs:Tapi_RiskParameterPac/';
            }
        }
        leaf _validation {
            type leafref {
                path '/TapiModule-ObjectClasses-TopologyPacs:Tapi_ValidationPac/';
            }
        }
        leaf _layerTransition {
            type leafref {
                path '/TapiModule-ObjectClasses-TopologyPacs:Tapi_LayerProtocolTransitionPac/';
            }
        }
    }
    grouping Tapi_NodeEdgePoint {
        description "The LogicalTerminationPoint (LTP) object class encapsulates the termination and adaptation functions of one or more transport layers. 
            The structure of LTP supports all transport protocols including circuit and packet forms.";
        list _layerProtocol {
            key 'localId';
            uses Tapi_LayerProtocol;
            min-elements 1;
        }
        leaf-list _clientNodeEdgePoint {
            type string;
        }
        leaf uuid {
            type TapiModule-TypeDefinitions:Tapi_UniversalId;
            description "UUID: An identifier that is universally unique
                (consider in the context of Identifier: A property of an entity/role with a value that is unique within an identifier space, where the identifier space is itself globally unique, and immutable. An identifier carries no semantics with respect to the purpose or state of the entity)";
        }
        list name {
            description "List of names. A property of an entity with a value that is unique in some namespace but may change during the life of the entity. A name carries no semantics with respect to the purpose of the entity.";
            uses TapiModule-TypeDefinitions:Tapi_NameAndValue;
            min-elements 1;
        }
        list label {
            description "List of labels.A property of an entity with a value that is not expected to be unique and is allowed to change. A label carries no semantics with respect to the purpose of the entity and has no effect on the entity behavior or state.";
            uses TapiModule-TypeDefinitions:Tapi_NameAndValue;
        }
        list extension {
            description "List of simple name-value extentions. Extension provides an opportunity to define properties not declared in the class that extend the class enabling a realization with simple ad-hoc extension of standard classes to be conformant.";
            uses TapiModule-TypeDefinitions:Tapi_NameAndValue;
        }
        leaf direction {
            type TapiModule-TypeDefinitions:Tapi_TerminationDirection;
        }
        leaf administrativeState {
            type TapiModule-TypeDefinitions:Tapi_AdministrativeState;
        }
        leaf operationalState {
            type TapiModule-TypeDefinitions:Tapi_OperationalState;
        }
        leaf lifecycleState {
            type TapiModule-TypeDefinitions:Tapi_LifecycleState;
        }
    }
    list Tapi_ServiceEndPoint {
        key 'uuid';
        uses Tapi_ServiceEndPoint;
    }
    grouping Tapi_ServiceEndPoint {
        description "The LogicalTerminationPoint (LTP) object class encapsulates the termination and adaptation functions of one or more transport layers. 
            The structure of LTP supports all transport protocols including circuit and packet forms.";
        list _layerProtocol {
            key 'localId';
            uses Tapi_LayerProtocol;
            min-elements 1;
        }
        leaf-list _mappedNodeEdgePoint {
            type leafref {
                path '/Tapi_Topology/_node/_ownedNodeEdgePoint/uuid';
            }
        }
        leaf uuid {
            type TapiModule-TypeDefinitions:Tapi_UniversalId;
            description "UUID: An identifier that is universally unique
                (consider in the context of Identifier: A property of an entity/role with a value that is unique within an identifier space, where the identifier space is itself globally unique, and immutable. An identifier carries no semantics with respect to the purpose or state of the entity)";
        }
        list label {
            description "List of labels.A property of an entity with a value that is not expected to be unique and is allowed to change. A label carries no semantics with respect to the purpose of the entity and has no effect on the entity behavior or state.";
            uses TapiModule-TypeDefinitions:Tapi_NameAndValue;
        }
        list name {
            description "List of names. A property of an entity with a value that is unique in some namespace but may change during the life of the entity. A name carries no semantics with respect to the purpose of the entity.";
            uses TapiModule-TypeDefinitions:Tapi_NameAndValue;
            min-elements 1;
        }
        list extension {
            description "List of simple name-value extentions. Extension provides an opportunity to define properties not declared in the class that extend the class enabling a realization with simple ad-hoc extension of standard classes to be conformant.";
            uses TapiModule-TypeDefinitions:Tapi_NameAndValue;
        }
        leaf direction {
            type TapiModule-TypeDefinitions:Tapi_TerminationDirection;
        }
        leaf operationalState {
            type TapiModule-TypeDefinitions:Tapi_OperationalState;
        }
    }
    list Tapi_ConnectionEndPoint {
        key 'uuid';
        uses Tapi_ConnectionEndPoint;
    }
    grouping Tapi_ConnectionEndPoint {
        description "The LogicalTerminationPoint (LTP) object class encapsulates the termination and adaptation functions of one or more transport layers. 
            The structure of LTP supports all transport protocols including circuit and packet forms.";
        list _layerProtocol {
            key 'localId';
            uses Tapi_LayerProtocol;
            min-elements 1;
        }
        leaf-list _clientNodeEdgePoint {
            type leafref {
                path '/Tapi_Topology/_node/_ownedNodeEdgePoint/uuid';
            }
        }
        leaf _serverNodeEdgePoint {
            type leafref {
                path '/Tapi_Topology/_node/_ownedNodeEdgePoint/uuid';
            }
        }
        leaf _peerConnectionEndPoint {
            type leafref {
                path '/Tapi_ConnectionEndPoint/uuid';
            }
        }
        leaf uuid {
            type TapiModule-TypeDefinitions:Tapi_UniversalId;
            description "UUID: An identifier that is universally unique
                (consider in the context of Identifier: A property of an entity/role with a value that is unique within an identifier space, where the identifier space is itself globally unique, and immutable. An identifier carries no semantics with respect to the purpose or state of the entity)";
        }
        list label {
            description "List of labels.A property of an entity with a value that is not expected to be unique and is allowed to change. A label carries no semantics with respect to the purpose of the entity and has no effect on the entity behavior or state.";
            uses TapiModule-TypeDefinitions:Tapi_NameAndValue;
        }
        list name {
            description "List of names. A property of an entity with a value that is unique in some namespace but may change during the life of the entity. A name carries no semantics with respect to the purpose of the entity.";
            uses TapiModule-TypeDefinitions:Tapi_NameAndValue;
            min-elements 1;
        }
        list extension {
            description "List of simple name-value extentions. Extension provides an opportunity to define properties not declared in the class that extend the class enabling a realization with simple ad-hoc extension of standard classes to be conformant.";
            uses TapiModule-TypeDefinitions:Tapi_NameAndValue;
        }
        leaf direction {
            type TapiModule-TypeDefinitions:Tapi_TerminationDirection;
        }
        leaf operationalState {
            type TapiModule-TypeDefinitions:Tapi_OperationalState;
        }
    }
    list Tapi_ConnectivityService {
        key 'uuid';
        uses Tapi_ConnectivityService;
    }
    grouping Tapi_ConnectivityService {
        description "The ForwardingConstruct (FC) object class models enabled potential for forwarding between two or more LTPs and like the LTP supports any transport protocol including all circuit and packet forms.
            At the lowest level of recursion, a FC represents a cross-connection within an NE.";
        list _servicePort {
            key 'localId';
            uses Tapi_ServicePort;
            min-elements 2;
        }
        list _connection {
            key 'uuid';
            uses Tapi_Connection;
        }
        leaf uuid {
            type TapiModule-TypeDefinitions:Tapi_UniversalId;
            description "UUID: An identifier that is universally unique
                (consider in the context of Identifier: A property of an entity/role with a value that is unique within an identifier space, where the identifier space is itself globally unique, and immutable. An identifier carries no semantics with respect to the purpose or state of the entity)";
        }
        list name {
            description "List of names. A property of an entity with a value that is unique in some namespace but may change during the life of the entity. A name carries no semantics with respect to the purpose of the entity.";
            uses TapiModule-TypeDefinitions:Tapi_NameAndValue;
            min-elements 1;
        }
        list label {
            description "List of labels.A property of an entity with a value that is not expected to be unique and is allowed to change. A label carries no semantics with respect to the purpose of the entity and has no effect on the entity behavior or state.";
            uses TapiModule-TypeDefinitions:Tapi_NameAndValue;
        }
        list extension {
            description "List of simple name-value extentions. Extension provides an opportunity to define properties not declared in the class that extend the class enabling a realization with simple ad-hoc extension of standard classes to be conformant.";
            uses TapiModule-TypeDefinitions:Tapi_NameAndValue;
        }
        leaf layerProtocolName {
            type TapiModule-TypeDefinitions:Tapi_LayerProtocolName;
        }
        leaf direction {
            type TapiModule-TypeDefinitions:Tapi_ForwardingDirection;
        }
        leaf administrativeState {
            type TapiModule-TypeDefinitions:Tapi_AdministrativeState;
        }
        leaf operationalState {
            type TapiModule-TypeDefinitions:Tapi_OperationalState;
        }
        leaf lifecycleState {
            type TapiModule-TypeDefinitions:Tapi_LifecycleState;
        }
    }
    grouping Tapi_Connection {
        description "The ForwardingConstruct (FC) object class models enabled potential for forwarding between two or more LTPs and like the LTP supports any transport protocol including all circuit and packet forms.
            At the lowest level of recursion, a FC represents a cross-connection within an NE.";
        list _connectionPort {
            key 'localId';
            uses Tapi_ConnectionPort;
            min-elements 2;
        }
        list _path {
            key 'localId';
            uses Tapi_Route;
        }
        leaf _node {
            type leafref {
                path '/Tapi_Topology/_node/uuid';
            }
        }
        leaf uuid {
            type TapiModule-TypeDefinitions:Tapi_UniversalId;
            description "UUID: An identifier that is universally unique
                (consider in the context of Identifier: A property of an entity/role with a value that is unique within an identifier space, where the identifier space is itself globally unique, and immutable. An identifier carries no semantics with respect to the purpose or state of the entity)";
        }
        list name {
            description "List of names. A property of an entity with a value that is unique in some namespace but may change during the life of the entity. A name carries no semantics with respect to the purpose of the entity.";
            uses TapiModule-TypeDefinitions:Tapi_NameAndValue;
            min-elements 1;
        }
        list label {
            description "List of labels.A property of an entity with a value that is not expected to be unique and is allowed to change. A label carries no semantics with respect to the purpose of the entity and has no effect on the entity behavior or state.";
            uses TapiModule-TypeDefinitions:Tapi_NameAndValue;
        }
        list extension {
            description "List of simple name-value extentions. Extension provides an opportunity to define properties not declared in the class that extend the class enabling a realization with simple ad-hoc extension of standard classes to be conformant.";
            uses TapiModule-TypeDefinitions:Tapi_NameAndValue;
        }
        leaf layerProtocolName {
            type TapiModule-TypeDefinitions:Tapi_LayerProtocolName;
        }
        leaf direction {
            type TapiModule-TypeDefinitions:Tapi_ForwardingDirection;
        }
        leaf operationalState {
            type TapiModule-TypeDefinitions:Tapi_OperationalState;
        }
        leaf lifecycleState {
            type TapiModule-TypeDefinitions:Tapi_LifecycleState;
        }
    }
    grouping Tapi_Route {
        description "The FC Route (FcRoute) object class models the individual routes of an FC. 
            The route of an FC object is represented by a list of FCs at a lower level. 
            Note that depending on the service supported by an FC, an the FC can have multiple routes.";
        leaf-list _lowerConnection {
            type leafref {
                path '/Tapi_ConnectivityService/_connection/uuid';
            }
            min-elements 1;
        }
        leaf localId {
            type string;
            description "An identifier that is unique in the context of some scope that is less than the global scope.
                (consider in the context of Identifier: A property of an entity/role with a value that is unique within an identifier space, where the identifier space is itself unique, and immutable. The identifier therefore represents the identity of the entity/role. An identifier carries no semantics with respect to the purpose of the entity.)";
        }
    }
    grouping Tapi_LinkPort {
        description "The association of the Link to LTPs is made via LinkEnd.
            The LinkEnd object class models the access to the Link function. 
            The traffic forwarding between the associated LinkEnds of the Link depends upon the type of Link.  
            In cases where there is resilience the LinkEnd may convey the resilience role of the access to the Link. 
            The Link can be considered as a component and the LinkEnd as a Port on that component";
        leaf _nodeEdgePoint {
            type leafref {
                path '/Tapi_Topology/_node/_ownedNodeEdgePoint/uuid';
            }
        }
        leaf localId {
            type string;
            description "An identifier that is unique in the context of some scope that is less than the global scope.
                (consider in the context of Identifier: A property of an entity/role with a value that is unique within an identifier space, where the identifier space is itself unique, and immutable. The identifier therefore represents the identity of the entity/role. An identifier carries no semantics with respect to the purpose of the entity.)";
        }
        leaf role {
            type TapiModule-TypeDefinitions:Tapi_PortRole;
            description "Each LinkEnd of the Link has a role (e.g., symmetric, hub, spoke, leaf, root)  in the context of the Link with respect to the Link function. ";
        }
        leaf direction {
            type TapiModule-TypeDefinitions:Tapi_PortDirection;
            description "The orientation of defined flow at the LinkEnd.";
        }
    }
    grouping Tapi_ServicePort {
        description "The association of the FC to LTPs is made via EndPoints.
            The EndPoint (EP) object class models the access to the FC function. 
            The traffic forwarding between the associated EPs of the FC depends upon the type of FC and may be associated with FcSwitch object instances.  
            In cases where there is resilience the EndPoint may convey the resilience role of the access to the FC. 
            It can represent a protected (resilient/reliable) point or a protecting (unreliable working or protection) point.
            The EP replaces the Protection Unit of a traditional protection model. 
            The ForwadingConstruct can be considered as a component and the EndPoint as a Port on that component";
        leaf _serviceEndPoint {
            type leafref {
                path '/Tapi_ServiceEndPoint/uuid';
            }
        }
        leaf localId {
            type string;
            description "An identifier that is unique in the context of some scope that is less than the global scope.
                (consider in the context of Identifier: A property of an entity/role with a value that is unique within an identifier space, where the identifier space is itself unique, and immutable. The identifier therefore represents the identity of the entity/role. An identifier carries no semantics with respect to the purpose of the entity.)";
        }
        leaf role {
            type TapiModule-TypeDefinitions:Tapi_PortRole;
            description "Each EP of the FC has a role (e.g., working, protection, protected, symmetric, hub, spoke, leaf, root)  in the context of the FC with respect to the FC function. ";
        }
        leaf direction {
            type TapiModule-TypeDefinitions:Tapi_PortDirection;
            description "The orientation of defined flow at the EndPoint.";
        }
        leaf serviceLayer {
            type TapiModule-TypeDefinitions:Tapi_LayerProtocolName;
        }
    }
    grouping Tapi_ConnectionPort {
        description "The association of the FC to LTPs is made via EndPoints.
            The EndPoint (EP) object class models the access to the FC function. 
            The traffic forwarding between the associated EPs of the FC depends upon the type of FC and may be associated with FcSwitch object instances.  
            In cases where there is resilience the EndPoint may convey the resilience role of the access to the FC. 
            It can represent a protected (resilient/reliable) point or a protecting (unreliable working or protection) point.
            The EP replaces the Protection Unit of a traditional protection model. 
            The ForwadingConstruct can be considered as a component and the EndPoint as a Port on that component";
        leaf _connectionEndPoint {
            type leafref {
                path '/Tapi_ConnectionEndPoint/uuid';
            }
        }
        leaf localId {
            type string;
            description "An identifier that is unique in the context of some scope that is less than the global scope.
                (consider in the context of Identifier: A property of an entity/role with a value that is unique within an identifier space, where the identifier space is itself unique, and immutable. The identifier therefore represents the identity of the entity/role. An identifier carries no semantics with respect to the purpose of the entity.)";
        }
        leaf role {
            type TapiModule-TypeDefinitions:Tapi_PortRole;
            description "Each EP of the FC has a role (e.g., working, protection, protected, symmetric, hub, spoke, leaf, root)  in the context of the FC with respect to the FC function. ";
        }
        leaf direction {
            type TapiModule-TypeDefinitions:Tapi_PortDirection;
            description "The orientation of defined flow at the EndPoint.";
        }
    }
    grouping Tapi_LayerProtocol {
        description "Each transport layer is represented by a LayerProtocol (LP) instance. The LayerProtocol instances it can be used for controlling termination and monitoring functionality. 
            It can also be used for controlling the adaptation (i.e. encapsulation and/or multiplexing of client signal), tandem connection monitoring, traffic conditioning and/or shaping functionality at an intermediate point along a connection. 
            Where the client – server relationship is fixed 1:1 and immutable, the layers can be encapsulated in a single LTP instance. Where the is a n:1 relationship between client and server, the layers must be split over two separate instances of LTP. ";
        leaf _lpSpec {
            type string;
            description "The LpSpec identifies the interna structure of the LP explaining internal flexibilities, degree of termination and degree of adaptation on both client and server side.";
        }
        leaf localId {
            type string;
            description "An identifier that is unique in the context of some scope that is less than the global scope.
                (consider in the context of Identifier: A property of an entity/role with a value that is unique within an identifier space, where the identifier space is itself unique, and immutable. The identifier therefore represents the identity of the entity/role. An identifier carries no semantics with respect to the purpose of the entity.)";
        }
        leaf layerProtocolName {
            type TapiModule-TypeDefinitions:Tapi_LayerProtocolName;
            description "Indicate the specific layer-protocol described by the LayerProtocol entity.";
        }
        leaf terminationDirection {
            type TapiModule-TypeDefinitions:Tapi_TerminationDirection;
            description "The overall directionality of the LP. 
                - A BIDIRECTIONAL LP will have some SINK and/or SOURCE flowss.
                - A SINK LP can only contain elements with SINK flows or CONTRA_DIRECTION_SOURCE flows
                - A SOURCE LP can only contain SOURCE flows or CONTRA_DIRECTION_SINK flows";
        }
        leaf terminationState {
            type TapiModule-TypeDefinitions:Tapi_TerminationState;
            description "Indicates whether the layer is terminated and if so how.";
        }
    }
    list Tapi_TeLink {
        uses Tapi_TeLink;
    }
    grouping Tapi_TeLink {
        description "The Link object class models effective adjacency between two or more ForwardingDomains (FD). ";
        leaf-list _node {
            type leafref {
                path '/Tapi_Topology/_node/uuid';
            }
            max-elements 2;
            min-elements 2;
        }
        leaf-list _linkPort {
            type leafref {
                path '/Tapi_Topology/_link/_linkPort/localId';
            }
            max-elements 2;
        }
        leaf _link {
            type leafref {
                path '/Tapi_Topology/_link/uuid';
            }
        }
        leaf uuid {
            type TapiModule-TypeDefinitions:Tapi_UniversalId;
            description "UUID: An identifier that is universally unique
                (consider in the context of Identifier: A property of an entity/role with a value that is unique within an identifier space, where the identifier space is itself globally unique, and immutable. An identifier carries no semantics with respect to the purpose or state of the entity)";
        }
    }
    list Tapi_Path {
        uses Tapi_Path;
    }
    grouping Tapi_Path {
        description "Path is described by an ordered list of TE Links. A TE Link is defined by a pair of Node/NodeEdgePoint IDs. A Connection is realized by concatenating link resources (associated with a Link) and the lower-level connections (cross-connections) in the different nodes";
        leaf-list _telink {
            type leafref {
                path '/Tapi_TeLink/';
            }
            min-elements 1;
        }
        leaf uuid {
            type TapiModule-TypeDefinitions:Tapi_UniversalId;
            description "UUID: An identifier that is universally unique
                (consider in the context of Identifier: A property of an entity/role with a value that is unique within an identifier space, where the identifier space is itself globally unique, and immutable. An identifier carries no semantics with respect to the purpose or state of the entity)";
        }
        container routingConstraint {
            uses TapiModule-TypeDefinitions:Tapi_ConnectivityConstraint;
        }
    }
}
