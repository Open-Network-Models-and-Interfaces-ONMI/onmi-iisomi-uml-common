module TapiModule-TypeDefinitions {
    namespace "uri:onf:TapiModule-TypeDefinitions";
    prefix TapiModule-TypeDefinitions;
    import TapiModule-ObjectClasses {
        prefix TapiModule-ObjectClasses;
    }
    revision 2016-06-19{}
    typedef Tapi_ServiceType {
        type enumeration {
            enum POINT_TO_POINT_CONNECTIVITY;
            enum POINT_TO_MULTIPOINT_CONNECTIVTY;
            enum MULTIPOINT_CONNECTIVITY;
        }
    }
    typedef Tapi_FixedCapacityValue {
        description "The Capacity (Bandwidth) values that are applicable for digital layers. ";
        type enumeration {
            enum NOT_APPLICABLE;
            enum 10MBPS;
            enum 100MBPS;
            enum 1GBPS;
            enum 2.4GBPS;
            enum 10GBPS;
            enum 40GBPS;
            enum 100GBPS;
            enum 200GBPS;
            enum 400GBPS;
        }
    }
    grouping Tapi_ConnectivityConstraint {
        leaf serviceType {
            type Tapi_ServiceType;
        }
        container requestedCapacity {
            uses Tapi_Capacity;
        }
        leaf serviceLevel {
            type string;
            description "An abstract value the meaning of which is mutually agreed – typically represents metrics such as - Class of service, priority, resiliency, availability";
        }
        leaf-list serviceLayer {
            type Tapi_LayerProtocolName;
        }
        list costCharacteristic {
            description "The list of costs where each cost relates to some aspect of the TopologicalEntity.";
            uses Tapi_CostCharacteristic;
        }
        list riskCharacteristic {
            description "A list of risk characteristics for consideration in an analysis of shared risk. Each element of the list represents a specific risk consideration.";
            uses Tapi_RiskCharacteristic;
        }
        list latencyCharacteristic {
            description "The effect on the latency of a queuing process. This only has significant effect for packet based systems and has a complex characteristic.";
            uses Tapi_QueuingLatency;
        }
        leaf-list includePath {
            type leafref {
                path '/TapiModule-ObjectClasses:Tapi_Path/';
            }
        }
        leaf-list excludePath {
            type leafref {
                path '/TapiModule-ObjectClasses:Tapi_Path/';
            }
        }
    }
    grouping Tapi_ScheduleInfo {
        leaf startTime {
            type string;
        }
        leaf endTime {
            type string;
        }
    }
    typedef Tapi_PortRole {
        description "The role of an end in the context of the function of the forwarding entity that it bounds
            Lifecycle : Preliminary";
        type enumeration {
            enum SYMMETRIC;
            enum ROOT;
            enum LEAF;
        }
    }
    typedef Tapi_LayerProtocolName {
        description "Provides a controlled list of layer protocol names and indicates the naming authority.
            Note that it is expected that attributes will be added to this structure to convey the naming authority name, the name of the layer protocol using a human readable string and any particular standard reference.
            Layer protocol names include:
            -    Layer 1 (L1): OTU, ODU
            -    Layer 2 (L2): Carrier Grade Ethernet (ETY, ETH), MPLS-TP (MT)
            ";
        type enumeration {
            enum OCH;
            enum ODU;
            enum ETH;
            enum MPLS_TP;
        }
    }
    grouping Tapi_NameAndValue {
        description "A scoped name-value pair";
        leaf valueName {
            type string;
            description "The name of the value. The value need not have a name.";
        }
        leaf value {
            type string;
            description "The value";
        }
        leaf _nameAndValueAuthorityRef {
            type string;
            description "The authority that defines the named value.";
        }
    }
    typedef Tapi_UniversalId {
        description "The univeral ID value where the mechanism for generation is defned by some authority not directly referenced in the structure.";
        type string;
    }
    typedef Tapi_ForwardingDirection {
        description "The directionality of a Forwarding entity.";
        type enumeration {
            enum BIDIRECTIONAL {
                description "The Fowarding entity supports both BIDIRECTIONAL flows at all Ports (i.e. all Ports have both an INPUT flow and an OUTPUT flow defined)";
            }
            enum UNIDIRECTIONAL {
                description "The Forwarding entity has Ports that are either INPUT or OUTPUT. It has no BIDIRECTIONAL Ports.";
            }
            enum UNDEFINED_OR_UNKNOWN {
                description "Not a normal state. The system is unable to determine the correct value.";
            }
        }
    }
    typedef Tapi_TerminationDirection {
        description "The directionality of a termination entity";
        type enumeration {
            enum BIDIRECTIONAL {
                description "A Termination with both SINK and SOURCE flows.";
            }
            enum SINK {
                description "The flow is up the layer stack from the server side to the client side. 
                    Considering an example of a Termination function within the termination entity, a SINK flow:
                    - will arrive at at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termiation can be bound to an OUTPUT Port of a Forwarding entity";
            }
            enum SOURCE {
                description "The flow is down the layer stack from the server side to the client side. 
                    Considering an example of a Termination function within the termination entity, a SOURCE flow:
                    - will arrive at at the top of the termination function (the client side) where it is essentially at an INPUT to the termination component
                    - then will be assembled with various overheads etc and will be coded 
                    - then coded form of the assembly of flow will be sent out of the termination function (the server side) where it is essentially at an OUTPUT from the termination component
                    A SOURCE termination is one that only supports a SOURCE flow.
                    A SOURCE termiation can be bound to an INPUT Port of a Forwarding entity";
            }
            enum UNDEFINED_OR_UNKNOWN {
                description "Not a normal state. The system is unable to determine the correct value.";
            }
        }
    }
    typedef Tapi_PortDirection {
        description "The orientation of flow at the Port of a Forwarding entity";
        type enumeration {
            enum BIDIRECTIONAL {
                description "The Port has both an INPUT flow and an OUTPUT flow defined.";
            }
            enum INPUT {
                description "The Port only has definition for a flow into the Forwarding entity (i.e. an ingress flow).";
            }
            enum OUTPUT {
                description "The Port only has definition for a flow out of the Forwarding entity (i.e. an egress flow).";
            }
            enum UNIDENTIFIED_OR_UNKNOWN {
                description "Not a normal state. The system is unable to determine the correct value.";
            }
        }
    }
    typedef Tapi_OperationalState {
        description "The possible values of the operationalState.
            Lifecycle : Preliminary";
        type enumeration {
            enum DISABLED {
                description "The resource is unable to meet the SLA of the user of the resource. If no (explicit) SLA is defined the resource is disabled if it is totally inoperable and unable to provide service to the user.";
            }
            enum ENABLED {
                description "The resource is partially or fully operable and available for use";
            }
        }
    }
    typedef Tapi_AdministrativeState {
        description "The possible values of the administrativeState.
            Lifecycle : Preliminary";
        type enumeration {
            enum LOCKED {
                description "Users are administratively prohibited from making use of the resource.";
            }
            enum UNLOCKED {
                description "Users are allowed to use the resource";
            }
        }
    }
    typedef Tapi_LifecycleState {
        description "The possible values of the lifecycleState.
            Lifecycle : Experimental";
        type enumeration {
            enum PLANNED {
                description "The resource is planned but is not present in the network.";
            }
            enum POTENTIAL {
                description "The supporting resources are present in the network but are shared with other clients; or require further configuration before they can be used; or both.
                    o    When a potential resource is configured and allocated to a client it is moved to the “installed” state for that client.
                    o    If the potential resource has been consumed (e.g. allocated to another client) it is moved to the “planned” state for all other clients.";
            }
            enum INSTALLED {
                description "The resource is present in the network and is capable of providing the service expected.";
            }
            enum PENDING_REMOVAL {
                description "The resource has been marked for removal";
            }
        }
    }
    typedef Tapi_TerminationState {
        description "Provides support for the range of behaviours and specific states that an LP can take with respect to termination of the signal.
            Indicates to what degree the LayerTermination is terminated.
            Lifecycle : Experimental";
        type enumeration {
            enum LP_CAN_NEVER_TERMINATE {
                description "A non-flexible case that can never be terminated.";
            }
            enum LT_NOT_TERMINATED {
                description "A flexible termination that can terminate but is currently not terminated.";
            }
            enum TERMINATED_SERVER_TO_CLIENT_FLOW {
                description "A flexible termination that is currently terminated for server to client flow only.";
            }
            enum TERMINATED_CLIENT_TO_SERVER_FLOW {
                description "A flexible termination that is currently terminated for client to server flow only.";
            }
            enum TERMINATED_BIDIRECTIONAL {
                description "A flexible termination that is currently terminated in both directions of flow.";
            }
            enum LT_PERMENANTLY_TERMINATED {
                description "A non-flexible termination that is always terminated (in both directions of flow for a bidirectional case and in the one direction of flow for both unidirectional cases).";
            }
            enum TERMINATION_STATE_UNKNOWN {
                description "There TerminationState cannot be determined.";
            }
        }
    }
    grouping Tapi_Capacity {
        description "Information on capacity of a particular TopologicalEntity.";
        leaf totalSize {
            type string;
            description "Total capacity of the TopologicalEntity in MB/s";
        }
        leaf maximumUsageInstances {
            type string;
            description "Where there is some limit to the number of client (e.g. in a channelized case).";
        }
        leaf maximumUsageSize {
            type string;
            description "Where a client is of variable capacity but due to some underlying realization the maximum size of the client is smaller than the totalSize.";
        }
        leaf numberingRange {
            type string;
            description "Method for identifying units of capacity via some numbering scheme.";
        }
    }
    grouping Tapi_CostCharacteristic {
        description "The information for a particular cost characteristic.";
        leaf costName {
            type string;
            description "The cost characteristic will related to some aspect of the TopologicalEntity (e.g. $ cost, routing weight). This aspect will be conveyed by the costName.";
        }
        leaf costValue {
            type string;
            description "The specific cost.";
        }
        leaf costAlgorithm {
            type string;
            description "The cost may vary based upon some properties of the TopologicalEntity. The rules for the variation are conveyed by the costAlgorithm.";
        }
    }
    grouping Tapi_QueuingLatency {
        description "Provides information on latency characteristic for a particular stated trafficProperty.";
        leaf trafficPropertyName {
            type string;
            description "The identifier of the specific traffic property to which the queuing latency applies.";
        }
        leaf latencyValue {
            type string;
            description "The specific queuing latency for the traffic property.";
        }
    }
    grouping Tapi_RiskCharacteristic {
        description "The information for a particular risk characteristic where there is a list of risk identifiers related to that characteristic.";
        leaf riskCharacteristicName {
            type string;
            description "The name of the risk characteristic. The characteristic may be related to a specific degree of closeness. 
                For example a particular characteristic may apply to failures that are localized (e.g. to one side of a road) where as another characteristic may relate to failures that have a broader impact (e.g. both sides of a road that crosses a bridge).
                Depending upon the importance of the traffic being routed different risk characteristics will be evaluated.";
        }
        leaf-list riskIdentifierList {
            description "A list of the identifiers of each physical/geographic unit (with the specific risk characteristic) that is related to a segment of the TopologicalEntity.";
            type string;
            min-elements 1;
        }
    }
    grouping Tapi_ValidationMechanism {
        description "Identifies the validation mechanism and describes the characteristics of that mechanism";
        leaf validationMechanism {
            type string;
            description "Name of mechanism used to validate adjacency";
        }
        leaf layerProtocolAdjacencyValidated {
            type string;
            description "State of validatiion";
        }
        leaf validationRobustness {
            type string;
            description "Quality of validation (i.e. how likely is the stated validation to be invalid)";
        }
    }
    grouping Tapi_PathOptimizationConstraint {
        leaf trafficInterruption {
            type Tapi_DirectiveValue;
        }
    }
    typedef Tapi_DirectiveValue {
        type enumeration {
            enum MINIMIZE;
            enum MAXIMIZE;
            enum ALLOW;
            enum DISALLOW;
            enum DONT_CARE;
        }
    }
    grouping Tapi_PathObjectiveFunction {
        leaf concurrentPaths {
            type Tapi_DirectiveValue;
        }
        leaf bandwidthOptimization {
            type Tapi_DirectiveValue;
        }
        leaf costOptimization {
            type Tapi_DirectiveValue;
        }
        leaf linkUtilization {
            type Tapi_DirectiveValue;
        }
        leaf resourceSharing {
            type Tapi_DirectiveValue;
        }
    }
}
