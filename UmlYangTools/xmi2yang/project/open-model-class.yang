// Contents of "OpenModelClassIdentity"
module open-model-class {
	namespace "urn:iisomi:open-model-class";
	prefix omc;
	organization "IISOMI";
	contact "eagle@community.opensourcesdn.org";
	description "This YANG module defines the root identity and the base identity
				references to hold the entity class and specification class names.";
	revision 2017-03-29 {
		description "Initial revision";
		reference "ONF-TR-531, RFC 6020 and RFC 6087";
	}

//************************************
// package default-identities
//************************************
	identity open-model-class-t {
		description
			"The identity of the single root for all
			 identities in the model. Note that section
			 7.18.2 in RFC7950 says that identity derivation is
			 irreflexive (i.e., an identity cannot be derived
			 from itself.";
	}
	
	grouping open-model-class-g {
		leaf entity-class {
			type identityref {
				base open-model-class-t;
			}
			description "The base identity reference to hold the entity class name";
		}
		leaf specification-class {
			type identityref {
				base open-model-class-t;
			}
			description "The base identity reference to hold the specification class name";
		}
		description "The grouping representing the OpenModelClass meta-data";
	}
}
