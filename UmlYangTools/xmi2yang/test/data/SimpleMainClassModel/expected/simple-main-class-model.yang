module simple-main-class-model {
    namespace "urn:onf:params:xml:ns:yang:simple-main-class-model";
    prefix simple-main-class-model;
    organization "ONF (Open Networking Foundation) IMP Working Group";
    contact "WG Web: <https://www.open{[]}networking.org/technical-communities/areas/services/>
        WG List: mailto: <wg list name>@opennetworking.org>,.
        WG Chair: your-WG-chair
            <mailto:your-WG-chair@example.com>
        Editor: your-name
            <mailto:your-email@example.com>";
    description "none";
    revision 2018-01-31 {
        description "Test revision";
        reference "Papyrus";
    }
    /***********************
    * package object-classes
    **********************/ 
        container main-class-1 {
            uses main-class-1;
            description "none";
        }
        grouping main-class-1 {
            leaf attribute-1 {
                type string;
                description "none";
            }
            list component-class {
                min-elements 1;
                uses component-class;
                description "none";
            }
            description "none";
        }
        container main-class-2 {
            uses main-class-2;
            description "none";
        }
        grouping main-class-2 {
            leaf attribute-2 {
                type string;
                description "none";
            }
            list component-class {
                min-elements 1;
                uses component-class;
                description "none";
            }
            description "none";
        }
        grouping component-class {
            leaf attribute-5 {
                type string;
                description "none";
            }
            leaf attribute-6 {
                type string;
                description "none";
            }
            description "none";
        }

}
