module tapi {
    namespace "urn:onf:params:xml:ns:yang:Tapi";
    prefix tapi;
    organization "ONF (Open Networking Foundation) IMP Working Group";
    contact "WG Web: <https://www.open{[]}networking.org/technical-communities/areas/services/>
        WG List: mailto: <wg list name>@opennetworking.org>,.
        WG Chair: your-WG-chair
            <mailto:your-WG-chair@example.com>
        Editor: your-name
            <mailto:your-email@example.com>";
    description "none";
    revision 2016-12-20 {
        description "Test revision";
        reference "Papyrus";
    }
    augment "/Tapi:Context/Tapi:_serviceEndPoint" {
        uses service-end-point;
        description "none";
    }
    /***********************
    * package object-classes
    **********************/ 
        grouping admin-state-pac {
            leaf administrative-state {
                type administrative-state;
                description "none";
            }
            leaf operational-state {
                type operational-state;
                description "none";
            }
            leaf lifecycle-state {
                type lifecycle-state;
                description "none";
            }
            description "Provides state attributes that are applicable to an entity that can be administered. Such an entity also has operational and lifecycle aspects.";
        }
        grouping global-class {
            leaf uuid {
                type universal-id;
                description "UUID: An identifier that is universally unique
                    (consider in the context of Identifier: A property of an entity/role with a value that is unique within an identifier space, where the identifier space is itself globally unique, and immutable. An identifier carries no semantics with respect to the purpose or state of the entity)";
            }
            list name {
                key 'value-name';
                min-elements 1;
                uses name-and-value;
                description "List of names. A property of an entity with a value that is unique in some namespace but may change during the life of the entity. A name carries no semantics with respect to the purpose of the entity.";
            }
            list label {
                key 'value-name';
                uses name-and-value;
                description "List of labels.A property of an entity with a value that is not expected to be unique and is allowed to change. A label carries no semantics with respect to the purpose of the entity and has no effect on the entity behavior or state.";
            }
            list extensions {
                key 'extensions-specification';
                config false;
                uses extensions-spec;
                description "none";
            }
            description "The TAPI GlobalComponent serves as the super class for all TAPI entities that can be directly retrieved by their ID. As such, these are first class entities and their ID is expected to be globally unique. ";
        }
        grouping layer-protocol {
            leaf layer-protocol-name {
                type layer-protocol-name;
                description "Indicate the specific layer-protocol described by the LayerProtocol entity.";
            }
            leaf termination-direction {
                type termination-direction;
                description "The overall directionality of the LP. 
                    - A BIDIRECTIONAL LP will have some SINK and/or SOURCE flowss.
                    - A SINK LP can only contain elements with SINK flows or CONTRA_DIRECTION_SOURCE flows
                    - A SOURCE LP can only contain SOURCE flows or CONTRA_DIRECTION_SINK flows";
            }
            leaf termination-state {
                type termination-state;
                description "Indicates whether the layer is terminated and if so how.";
            }
            uses local-class;
            description "Each transport layer is represented by a LayerProtocol (LP) instance. The LayerProtocol instances it can be used for controlling termination and monitoring functionality. 
                It can also be used for controlling the adaptation (i.e. encapsulation and/or multiplexing of client signal), tandem connection monitoring, traffic conditioning and/or shaping functionality at an intermediate point along a connection. 
                Where the client – server relationship is fixed 1:1 and immutable, the layers can be encapsulated in a single LTP instance. Where the is a n:1 relationship between client and server, the layers must be split over two separate instances of LTP. ";
        }
        grouping lifecycle-state-pac {
            leaf lifecycle-state {
                type lifecycle-state;
                description "none";
            }
            description "Provides state attributes for an entity that has lifeccycle aspects only.";
        }
        grouping local-class {
            leaf local-id {
                type string;
                description "none";
            }
            list extensions {
                key 'extensions-specification';
                config false;
                uses extensions-spec;
                description "none";
            }
            description "The TAPI GlobalComponent serves as the super class for all TAPI entities that can be directly retrieved by their ID. As such, these are first class entities and their ID is expected to be globally unique. ";
        }
        grouping operational-state-pac {
            leaf operational-state {
                type operational-state;
                description "none";
            }
            leaf lifecycle-state {
                type lifecycle-state;
                description "none";
            }
            description "Provides state attributes that are applicable to an entity that reflects operational aspects. Such an entity is expected to also have lifecycle aspects.";
        }
        grouping time-range {
            leaf end-time {
                type date-and-time;
                description "none";
            }
            leaf start-time {
                type date-and-time;
                description "none";
            }
            description "none";
        }
        grouping extensions-spec {
            description "none";
        }
        container context {
            uses context;
            description "none";
        }
        grouping context {
            container nw-topology-service {
                config false;
                uses service-spec;
                description "none";
            }
            list connectivity-service {
                key 'uuid';
                uses service-spec;
                description "none";
            }
            list vnw-service {
                key 'uuid';
                uses service-spec;
                description "none";
            }
            list path-comp-service {
                key 'uuid';
                uses service-spec;
                description "none";
            }
            list notif-subscription {
                key 'uuid';
                uses service-spec;
                description "none";
            }
            list service-end-point {
                key 'uuid';
                config false;
                min-elements 2;
                uses resource-spec;
                description "none";
            }
            list topology {
                key 'uuid';
                config false;
                uses resource-spec;
                description "none";
            }
            list connection {
                key 'uuid';
                config false;
                uses resource-spec;
                description "none";
            }
            list path {
                key 'uuid';
                config false;
                uses resource-spec;
                description "none";
            }
            list notification {
                key 'uuid';
                config false;
                uses resource-spec;
                description "none";
            }
            uses global-class;
            description "The Network Control Domain (NCD) object class represents the scope of control that a particular SDN controller has with respect to a particular network, (i.e., encompassing a designated set of interconnected (virtual) network elements).";
        }
        grouping resource-spec {
            uses global-class;
            description "none";
        }
        grouping service-spec {
            uses global-class;
            description "none";
        }
        grouping service-end-point {
            list layer-protocol {
                key 'local-id';
                config false;
                min-elements 1;
                uses layer-protocol;
                description "none";
            }
            container state {
                config false;
                uses lifecycle-state-pac;
                description "none";
            }
            leaf direction {
                type termination-direction;
                config false;
                description "none";
            }
            uses resource-spec;
            description "The LogicalTerminationPoint (LTP) object class encapsulates the termination and adaptation functions of one or more transport layers. 
                The structure of LTP supports all transport protocols including circuit and packet forms.";
        }

    /***********************
    * package type-definitions
    **********************/ 
        typedef administrative-state {
            type enumeration {
                enum locked {
                    description "Users are administratively prohibited from making use of the resource.";
                }
                enum unlocked {
                    description "Users are allowed to use the resource";
                }
            }
            description "The possible values of the administrativeState.";
        }
        typedef date-and-time {
            type string;
            description "This primitive type defines the date and time according to the following structure:
                yyyyMMddhhmmss.s[Z|{+|-}HHMm] where:
                yyyy    0000..9999    year
                MM    01..12            month
                dd        01..31            day
                hh        00..23            hour
                mm    00..59            minute
                ss        00..59            second
                s        .0...9            tenth of second (set to .0 if EMS or NE cannot support this granularity)
                Z        Z                indicates UTC (rather than local time)
                {+|-}    + or -            delta from UTC
                HH        00..23            time zone difference in hours
                Mm    00..59            time zone difference in minutes.";
        }
        typedef directive-value {
            type enumeration {
                enum minimize {
                    description "none";
                }
                enum maximize {
                    description "none";
                }
                enum allow {
                    description "none";
                }
                enum disallow {
                    description "none";
                }
                enum dont-care {
                    description "none";
                }
            }
            description "none";
        }
        typedef forwarding-direction {
            type enumeration {
                enum bidirectional {
                    description "The Fowarding entity supports both BIDIRECTIONAL flows at all Ports (i.e. all Ports have both an INPUT flow and an OUTPUT flow defined)";
                }
                enum unidirectional {
                    description "The Forwarding entity has Ports that are either INPUT or OUTPUT. It has no BIDIRECTIONAL Ports.";
                }
                enum undefined-or-unknown {
                    description "Not a normal state. The system is unable to determine the correct value.";
                }
            }
            description "The directionality of a Forwarding entity.";
        }
        typedef layer-protocol-name {
            type enumeration {
                enum och {
                    description "none";
                }
                enum odu {
                    description "none";
                }
                enum eth {
                    description "none";
                }
                enum mpls-tp {
                    description "none";
                }
            }
            description "Provides a controlled list of layer protocol names and indicates the naming authority.
                Note that it is expected that attributes will be added to this structure to convey the naming authority name, the name of the layer protocol using a human readable string and any particular standard reference.
                Layer protocol names include:
                -    Layer 1 (L1): OTU, ODU
                -    Layer 2 (L2): Carrier Grade Ethernet (ETY, ETH), MPLS-TP (MT)
                ";
        }
        typedef lifecycle-state {
            type enumeration {
                enum planned {
                    description "The resource is planned but is not present in the network.";
                }
                enum potential {
                    description "The supporting resources are present in the network but are shared with other clients; or require further configuration before they can be used; or both.
                        o    When a potential resource is configured and allocated to a client it is moved to the “installed” state for that client.
                        o    If the potential resource has been consumed (e.g. allocated to another client) it is moved to the “planned” state for all other clients.";
                }
                enum installed {
                    description "The resource is present in the network and is capable of providing the service expected.";
                }
                enum pending-removal {
                    description "The resource has been marked for removal";
                }
            }
            description "The possible values of the lifecycleState.";
        }
        grouping name-and-value {
            leaf value-name {
                type string;
                description "The name of the value. The value need not have a name.";
            }
            leaf value {
                type string;
                description "The value";
            }
            description "A scoped name-value pair";
        }
        typedef operational-state {
            type enumeration {
                enum disabled {
                    description "The resource is unable to meet the SLA of the user of the resource. If no (explicit) SLA is defined the resource is disabled if it is totally inoperable and unable to provide service to the user.";
                }
                enum enabled {
                    description "The resource is partially or fully operable and available for use";
                }
            }
            description "The possible values of the operationalState.";
        }
        typedef port-direction {
            type enumeration {
                enum bidirectional {
                    description "The Port has both an INPUT flow and an OUTPUT flow defined.";
                }
                enum input {
                    description "The Port only has definition for a flow into the Forwarding entity (i.e. an ingress flow).";
                }
                enum output {
                    description "The Port only has definition for a flow out of the Forwarding entity (i.e. an egress flow).";
                }
                enum unidentified-or-unknown {
                    description "Not a normal state. The system is unable to determine the correct value.";
                }
            }
            description "The orientation of flow at the Port of a Forwarding entity";
        }
        typedef port-role {
            type enumeration {
                enum symmetric {
                    description "none";
                }
                enum root {
                    description "none";
                }
                enum leaf {
                    description "none";
                }
                enum unknown {
                    description "none";
                }
            }
            description "The role of an end in the context of the function of the forwarding entity that it bounds";
        }
        typedef termination-direction {
            type enumeration {
                enum bidirectional {
                    description "A Termination with both SINK and SOURCE flows.";
                }
                enum sink {
                    description "The flow is up the layer stack from the server side to the client side. 
                        Considering an example of a Termination function within the termination entity, a SINK flow:
                        - will arrive at at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termiation can be bound to an OUTPUT Port of a Forwarding entity";
                }
                enum source {
                    description "The flow is down the layer stack from the server side to the client side. 
                        Considering an example of a Termination function within the termination entity, a SOURCE flow:
                        - will arrive at at the top of the termination function (the client side) where it is essentially at an INPUT to the termination component
                        - then will be assembled with various overheads etc and will be coded 
                        - then coded form of the assembly of flow will be sent out of the termination function (the server side) where it is essentially at an OUTPUT from the termination component
                        A SOURCE termination is one that only supports a SOURCE flow.
                        A SOURCE termiation can be bound to an INPUT Port of a Forwarding entity";
                }
                enum undefined-or-unknown {
                    description "Not a normal state. The system is unable to determine the correct value.";
                }
            }
            description "The directionality of a termination entity";
        }
        typedef termination-state {
            type enumeration {
                enum lp-can-never-terminate {
                    description "A non-flexible case that can never be terminated.";
                }
                enum lt-not-terminated {
                    description "A flexible termination that can terminate but is currently not terminated.";
                }
                enum terminated-server-to-client-flow {
                    description "A flexible termination that is currently terminated for server to client flow only.";
                }
                enum terminated-client-to-server-flow {
                    description "A flexible termination that is currently terminated for client to server flow only.";
                }
                enum terminated-bidirectional {
                    description "A flexible termination that is currently terminated in both directions of flow.";
                }
                enum lt-permenantly-terminated {
                    description "A non-flexible termination that is always terminated (in both directions of flow for a bidirectional case and in the one direction of flow for both unidirectional cases).";
                }
                enum termination-state-unknown {
                    description "There TerminationState cannot be determined.";
                }
            }
            description "Provides support for the range of behaviours and specific states that an LP can take with respect to termination of the signal.
                Indicates to what degree the LayerTermination is terminated.";
        }
        typedef universal-id {
            type string;
            description "The univeral ID value where the mechanism for generation is defned by some authority not directly referenced in the structure.";
        }

}
