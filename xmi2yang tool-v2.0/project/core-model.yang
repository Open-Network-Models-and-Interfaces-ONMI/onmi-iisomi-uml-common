module core-model {
    namespace "urn:onf:params:xml:ns:yang:CoreModel";
    prefix core-model;
    organization "ONF (Open Networking Foundation) IMP Working Group";
    contact "WG Web: <https://www.open{[]}networking.org/technical-communities/areas/services/>
        WG List: mailto: <wg list name>@opennetworking.org>,.
        WG Chair: your-WG-chair
            <mailto:your-WG-chair@example.com>
        Editor: your-name
            <mailto:your-email@example.com>";
    description "none";
    revision 2016-12-20 {
        description "Test revision";
        reference "Papyrus";
    }
    /***********************
    * package core-network-module
    **********************/ 
        /***********************
        * package type-definitions
        **********************/ 
            /***********************
            * package topology-pacs
            **********************/ 
                grouping cost-characteristics {
                    leaf cost-name {
                        type string;
                        description "The cost characteristic will related to some aspect of the TopologicalEntity (e.g. $ cost, routing weight). This aspect will be conveyed by the costName.";
                    }
                    leaf cost-value {
                        type string;
                        description "The specific cost.";
                    }
                    leaf cost-algorithm {
                        type string;
                        description "The cost may vary based upon some properties of the TopologicalEntity. The rules for the variation are conveyed by the costAlgorithm.";
                    }
                    description "The information for a particular cost characteristic.";
                }
                grouping risk-characteristic {
                    leaf risk-characteristic-name {
                        type string;
                        description "The name of the risk characteristic. The characteristic may be related to a specific degree of closeness. 
                            For example a particular characteristic may apply to failures that are localized (e.g. to one side of a road) where as another characteristic may relate to failures that have a broader impact (e.g. both sides of a road that crosses a bridge).
                            Depending upon the importance of the traffic being routed different risk characteristics will be evaluated.";
                    }
                    leaf-list risk-identifier-list {
                        type string;
                        min-elements 1;
                        description "A list of the identifiers of each physical/geographic unit (with the specific risk characteristic) that is related to a segment of the TopologicalEntity.";
                    }
                    description "The information for a particular risk characteristic where there is a list of risk identifiers related to that characteristic.";
                }
                grouping capacity {
                    leaf total-size {
                        type string;
                        description "Total capacity of the TopologicalEntity in MB/s";
                    }
                    leaf number-of-client-instances {
                        type string;
                        description "Where there is some limit to the number of client (e.g. in a channelized case).";
                    }
                    leaf maximum-client-size {
                        type string;
                        description "Where a client is of variable capacity but due to some underlying realization the maximum size of the client is smaller than the totalSize.";
                    }
                    leaf numbering-range {
                        type string;
                        description "Method for identifying units of capacity via some numbering scheme.";
                    }
                    description "Informtion on capacity of a particular TopologicalEntity.";
                }
                grouping validation-mechanism {
                    leaf validation-mechanism {
                        type string;
                        description "Name of mechanism used to validate adjacency";
                    }
                    leaf layer-protocol-adjacency-validated {
                        type string;
                        description "State of validatiion";
                    }
                    leaf validation-robustness {
                        type string;
                        description "Quality of validation (i.e. how likely is the stated validation to be invalid)";
                    }
                    description "Identifies the validation mechanism and describes the characteristics of that mechanism";
                }
                grouping queuing-latency {
                    leaf traffic-property {
                        type string;
                        description "The identifier of the specific traffic property to which the queuing latency applies.";
                    }
                    leaf latency-for-traffic-with-property {
                        type string;
                        description "The specific queuing latency for the traffic property.";
                    }
                    description "Provides information on latency characteristic for a particular stated trafficProperty.";
                }

            typedef operational-state {
                type enumeration {
                    enum enabled {
                        description "none";
                    }
                    enum disabled {
                        description "none";
                    }
                }
                description "OBSOLETE: The list of valid operational states for the connection.";
            }
            typedef oper-type {
                type enumeration {
                    enum revertive {
                        description "Traffic will return to a preferred route on recovery of that route (potentiall after some hold-off time)";
                    }
                    enum non-revertive {
                        description "Traffic will be rerouted on failure and not on recovery of any particular route.";
                    }
                }
                description "The operation type associated with the protection mechanism (either non-revertive or revertive).";
            }
            typedef directionality {
                type enumeration {
                    enum sink {
                        description "none";
                    }
                    enum source {
                        description "none";
                    }
                    enum bidirectional {
                        description "none";
                    }
                }
                description "OBSOLETE: The enumeration with the options for directionality of the termination point.";
            }
            typedef layer-protocol-name {
                type string;
                description "Provides a controlled list of layer protocol names and indicates the naming authority.
                    Note that it is expected that attributes will be added to this structure to convey the naming authority name, the name of the layer protocol using a human readable string and any particular standard reference.
                    Layer protocol names include:
                    -    Layer 1 (L1): OTU, ODU
                    -    Layer 2 (L2): Carrier Grade Ethernet (ETY, ETH), MPLS-TP (MT)
                    ";
            }
            typedef port-role {
                type string;
                description "The role of a port in the context of the function of the forwarding entity that it bounds";
            }
            typedef port-direction {
                type enumeration {
                    enum bidirectional {
                        description "The Port has both an INPUT flow and an OUTPUT flow defined.";
                    }
                    enum input {
                        description "The Port only has definition for a flow into the Forwarding entity (i.e. an ingress flow).";
                    }
                    enum output {
                        description "The Port only has definition for a flow out of the Forwarding entity (i.e. an egress flow).";
                    }
                    enum unidentified-or-unknown {
                        description "Not a normal state. The system is unable to determine the correct value.";
                    }
                }
                description "The orientation of flow at the Port of a Forwarding entity";
            }
            typedef forwarding-direction {
                type enumeration {
                    enum bidirectional {
                        description "The Fowarding entity supports both BIDIRECTIONAL flows at all Ports (i.e. all Ports have both an INPUT flow and an OUTPUT flow defined)";
                    }
                    enum unidirectional {
                        description "The Forwarding entity has Ports that are either INPUT or OUTPUT. It has no BIDIRECTIONAL Ports.";
                    }
                    enum undefined-or-unknown {
                        description "Not a normal state. The system is unable to determine the correct value.";
                    }
                }
                description "The directionality of a Forwarding entity.";
            }
            typedef termination-direction {
                type enumeration {
                    enum bidirectional {
                        description "A Termination with both SINK and SOURCE flows.";
                    }
                    enum sink {
                        description "The flow is up the layer stack from the server side to the client side. 
                            Considering an example of a Termination function within the termination entity, a SINK flow:
                            - will arrive at at the base of the termination function (the server side) where it is essentially at an INPUT to the termination component
                            - then will be decoded and deconstructed 
                            - then relevant parts of the flow will be sent out of the termination function (the client side) where it is essentially at an OUTPUT from the termination component
                            A SINK termination is one that only supports a SINK flow.
                            A SINK termiation can be bound to an OUTPUT Port of a Forwarding entity";
                    }
                    enum source {
                        description "The flow is down the layer stack from the server side to the client side. 
                            Considering an example of a Termination function within the termination entity, a SOURCE flow:
                            - will arrive at at the top of the termination function (the client side) where it is essentially at an INPUT to the termination component
                            - then will be assembled with various overheads etc and will be coded 
                            - then coded form of the assembly of flow will be sent out of the termination function (the server side) where it is essentially at an OUTPUT from the termination component
                            A SOURCE termination is one that only supports a SOURCE flow.
                            A SOURCE termiation can be bound to an INPUT Port of a Forwarding entity";
                    }
                    enum undefined-or-unknown {
                        description "Not a normal state. The system is unable to determine the correct value.";
                    }
                }
                description "The directionality of a termination entity";
            }
            typedef extended-termination-direction {
                type enumeration {
                    enum bidirectional {
                        description "A Termination with both SINK and SOURCE flows.";
                    }
                    enum sink {
                        description "The flow is up the layer stack from the server side to the client side. 
                            Considering an example of a Termination function within the termination entity, a SINK flow:
                            - will arrive at at the base of the termination function (the server side) where it is essentially at an INPUT to the termination component
                            - then will be decoded and deconstructed 
                            - then relevant parts of the flow will be sent out of the termination function (the client side) where it is essentially at an OUTPUT from the termination component
                            A SINK termination is one that only supports a SINK flow.
                            A SINK termiation can be bound to an OUTPUT Port of a Forwarding entity";
                    }
                    enum source {
                        description "The flow is down the layer stack from the server side to the client side. 
                            Considering an example of a Termination function within the termination entity, a SOURCE flow:
                            - will arrive at at the top of the termination function (the client side) where it is essentially at an INPUT to the termination component
                            - then will be assembled with various overheads etc and will be coded 
                            - then coded form of the assembly of flow will be sent out of the termination function (the server side) where it is essentially at an OUTPUT from the termination component
                            A SOURCE termination is one that only supports a SOURCE flow.
                            A SOURCE termiation can be bound to an INPUT Port of a Forwarding entity";
                    }
                    enum undefined-or-unknown {
                        description "Not a normal state. The system is unable to determine the correct value.";
                    }
                    enum contra-direction-sink {
                        description "The essential flow of the Termination entity is SINK (i.e. up the layer stack) but the INPUT flow of the Termination entity was provided by a SOURCE OUTPUT or taken from a SOURCE INPUT (duplicating the input signal) hence reversing the flow orientation from down the layer stack to up the layer stack.";
                    }
                    enum contra-direction-source {
                        description "The essential flow of the Termination entity is SOURCE (i.e. down the layer stack) but the OUTPUT flow of the Termination entity was fed to (and replaces) a SINK OUTPUT or was fed to a SINK INPUT (replacing the normal flow) hence reversing the flow orientation from down the layer stack to up the layer stack.";
                    }
                }
                description "Extended to include contra-direction considerations. Only applies to LP and elements of LP not to LTP??";
            }
            typedef protection-type {
                type string;
                description "Identifies the type of rotection of an FcSwitch.";
            }
            typedef termination-state {
                type enumeration {
                    enum lp-can-never-terminate {
                        description "A non-flexible case that can never be terminated.";
                    }
                    enum lt-not-terminated {
                        description "A flexible termination that can terminate but is currently not terminated.";
                    }
                    enum terminated-server-to-client-flow {
                        description "A flexible termination that is currently terminated for server to client flow only.";
                    }
                    enum terminated-client-to-server-flow {
                        description "A flexible termination that is currently terminated for client to server flow only.";
                    }
                    enum terminated-bidirectional {
                        description "A flexible termination that is currently terminated in both directions of flow.";
                    }
                    enum lt-permenantly-terminated {
                        description "A non-flexible termination that is always terminated (in both directions of flow for a bidirectional case and in the one direction of flow for both unidirectional cases).";
                    }
                    enum termination-state-unknown {
                        description "There TerminationState cannot be determined.";
                    }
                }
                description "Provides support for the range of behaviours and specific states that an LP can take with respect to termination of the signal.
                    Indicates to what degree the LayerTermination is terminated.";
            }

        /***********************
        * package object-classes
        **********************/ 
            /***********************
            * package topology-pacs
            **********************/ 
                grouping transfer-cost-pac {
                    list cost-characteristic-list {
                        min-elements 1;
                        uses cost-characteristics;
                        description "The list of costs where each cost relates to some aspect of the TopologicalEntity.";
                    }
                    description "The cost characteristics of a TopologicalEntity not necessarily correlated to the cost of the underlying physical realization. 
                        They may be quite specific to the individual TopologicalEntity e.g. opportunity cost. Relates to layer capacity
                        There may be many perspectives from which cost may be considered  for a particular TopologicalEntity and hence many specific costs and potentially cost algorithms. 
                        Using an entity will incur a cost. ";
                }
                grouping risk-parameter-pac {
                    list risk-characteristic-list {
                        min-elements 1;
                        uses risk-characteristic;
                        description "A list of risk characteristics for consideration in an analysis of shared risk. Each element of the list represents a specific risk consideration.";
                    }
                    description "The risk characteristics of a TopologicalEntity come directly from the underlying physical realization. 
                        The risk characteristics propagate from the physical realization to the client and from the server layer to the client layer, this propagation may be modified by protection.
                        A TopologicalEntity may suffer degradation or failure as a result of a problem in a part of the underlying realization.
                        The realization can be partitioned into segments which have some relevant common failure modes.
                        There is a risk of failure/degradation of each segment of the underlying realization.
                        Each segment is a part of a larger physical/geographical unit that behaves as one with respect to failure (i.e. a failure will have a high probability of impacting the whole unit (e.g. all cables in the same duct).
                        Disruptions to that larger physical/geographical unit will impact (cause failure/errors to) all TopologicalEntities that use any part of that larger physical/geographical entity.
                        Any TopologicalEntity that uses any part of that larger physical/geographical unit will suffer impact and hence each TopologicalEntity shares risk.
                        The identifier of each physical/geographical unit that is involved in the realization of each segment of a Topological entity can be listed in the RiskParameter_Pac of that TopologicalEntity.
                        A segment has one or more risk characteristic.
                        Shared risk between two TopologicalEntities compromises the integrity of any solution that use one of those TopologicalEntity as a backup for the other.
                        Where two TopologicalEntities have a common risk characteristic they have an elevated probability of failing simultaneously compared to two TopologicalEntities that do not share risk characteristics.";
                }
                grouping layer-protocol-transition-pac {
                    leaf-list transitioned-layer-protocol-list {
                        type string;
                        min-elements 1;
                        description "Provides the ordered structure of layer protocol transitions encapsulated in the TopologicalEntity. The ordering relates to the LinkPort role.";
                    }
                    leaf-list ltp-ref-list {
                        type leafref {
                            path '/core-model:network-control-domain/core-model:network-element-ref-list/core-model:ltp-ref-list/';
                        }
                        min-elements 1;
                        description "Lists the LTPs that define the layer protocol transition of the transitional link.";
                    }
                    description "Relevant for a Link that is formed by abstracting one or more LTPs (in a stack) to focus on the flow and deemphasize the protocol transformation. 
                        This abstraction is relevant when considering multi-layer routing. 
                        The layer protocols of the LTP and the order of their application to the signal is still relevant and need to be accounted for. This is derived from the LTP spec details.
                        This Pac provides the relevant abstractions of the LTPs and provides the necessary association to the LTPs involved.
                        Links that included details in this Pac are often referred to as Transitional Links.";
                }
                grouping transfer-timing-pac {
                    leaf fixed-latency-characteristic {
                        type string;
                        description "A TopologicalEntity suffers delay caused by the realization of the servers (e.g. distance related; FEC encoding etc.) along with some client specific processing. This is the total average latency effect of the TopologicalEntity";
                    }
                    leaf jitter-characteristic {
                        if-feature Present if jitterCharacteristics information is relevant to usage and statement can be made that applies equally to all flows that can be supported by the TopologicalEntity.
Note that if jitterCharacteristics is relevant but consistent ststement cannot be made then the TopologicalEntity should be described in terms of subordinate parts against which coherent statements can be made.
Note that this only applies to TDM.;
                        type string;
                        description "High frequency deviation from true periodicity of a signal and therefore a small high rate of change of transfer latency.
                            Applies to TDM systems (and not packet).";
                    }
                    leaf wander-characteristic {
                        if-feature Present if wanderCharacteristics information is relevant to usage and statement can be made that applies equally to all flows that can be supported by the TopologicalEntity.
Note that if wanderCharacteristics is relevant but consistent ststement cannot be made then the TopologicalEntity should be described in terms of subordinate parts against which coherent statements can be made.
Note that this only applies to TDM.;
                        type string;
                        description "Low frequency deviation from true periodicity of a signal and therefore a small low rate of change of transfer latency.
                            Applies to TDM systems (and not packet).";
                    }
                    list queuing-latency-list {
                        if-feature Present if queuingLatencyCharacteristics information is relevant to usage and statement can be made that applies equally to all flows that can be supported by the TopologicalEntity.
There may be more than one instance if the queuing behavior depends upon traffic properties.
Note that if queuingLatencyCharacteristics is relevant but consistent statement cannot be made then the TopologicalEntity should be described in terms of subordinate parts against which coherent statements can be made.
Note that this only applies to packet system.;
                        uses queuing-latency;
                        description "The effect on the latency of a queuing process. This only has significant effect for packet based systems and has a complex characteristic.";
                    }
                    description "A TopologicalEntity will suffer effects from the underlying physical realization related to the timing of the information passed by the TopologicalEntity.";
                }
                grouping transfer-integrity-pac {
                    leaf error-characteristic {
                        if-feature Present if errorCharacteristics information is relevant to usage and statement can be made that applies equally to all flows that can be supported by the TopologicalEntity.
Note that if errorCharacteristics is relevant but consistent ststement cannot be made then the TopologicalEntity should be described in terms of subordinate parts against which coherent statements can be made.
Note that this only applies to TDM.;
                        type string;
                        description "Describes the degree to which the signal propagated can be errored. 
                            Applies to TDM systems as the errored signal will be propagated and not packet as errored packets will be discarded.";
                    }
                    leaf loss-characteristic {
                        if-feature Present if lossCharacteristics information is relevant to usage and statement can be made that applies equally to all flows that can be supported by the TopologicalEntity.
Note that if lossCharacteristics is relevant but consistent ststement cannot be made then the TopologicalEntity should be described in terms of subordinate parts against which coherent statements can be made.
Note that this only applies to packet systems.;
                        type string;
                        description "Describes the acceptable characteristic of lost packets where loss may result from discard due to errors or overflow.
                            Applies to packet systems and not TDM (as for TDM errored signals are propagated unless grossly errored and overflow/underflow turns into timing slips).";
                    }
                    leaf repeat-delivery-characteristic {
                        if-feature Present if repeatCharacteristics information is relevant to usage and statement can be made that applies equally to all flows that can be supported by the TopologicalEntity.
Note that if repeatCharacteristics is relevant but consistent ststement cannot be made then the TopologicalEntity should be described in terms of subordinate parts against which coherent statements can be made.
Note that this primarily applies to packet systemswhere a packet may be delivered more than once (in fault recovery for example). 
Note that it can also apply to TDM where several frames may  be received twice due to switching in a system with a large differential propagation delay.;
                        type string;
                        description "Primarily applies to packet systems where a packet may be delivered more than once (in fault recovery for example). 
                            It can also apply to TDM where several frames may be received twice due to switching in a system with a large differential propagation delay.";
                    }
                    leaf delivery-order-characteristic {
                        if-feature Present if deliveryOrderCharacteristics information is relevant to usage and statement can be made that applies equally to all flows that can be supported by the TopologicalEntity.
Note that if deliveryOrderCharacteristics is relevant but consistent ststement cannot be made then the TopologicalEntity should be described in terms of subordinate parts against which coherent statements can be made.
Note that this only applies to packet systems.
;
                        type string;
                        description "Describes the degree to which packets will be delivered out of sequence.
                            Does not apply to TDM as the TDM protocols maintain strict order.";
                    }
                    leaf unavailable-time-characteristic {
                        type string;
                        description "Describes the duration for which there may be no valid signal propagated.";
                    }
                    leaf server-integrity-process-characteristic {
                        if-feature Present if serverIntegrityProcessCharacteristics information is relevant to usage and statement can be made that applies equally to all flows that can be supported by the TopologicalEntity.
Note that if serverIntegrityProcessCharacteristics is relevant but consistent ststement cannot be made then the TopologicalEntity should be described in terms of subordinate parts against which coherent statements can be made.
Note that this only applies where the server has some error recovery mechanism alters the characteristics of the link from a normal distribution.;
                        type string;
                        description "Describes the effect of any server integrity enhancement process on the characteristics of the TopologicalEntity.";
                    }
                    description "Transfer intergrity characteristic covers expected/specified/acceptable characteristic of degradation of the transfered signal.
                        It includes all aspects of possible degradation of signal content as well as any damage of any form to the total TopologicalEntity and to the carried signals.
                        Note that the statement is of total impact to the TopologicalEntity so any partial usage of the TopologicalEntity (e.g. a signal that does not use full capacity) will only suffer its portion of the impact.";
                }
                grouping transfer-capacity-pac {
                    container total-potential-capacity {
                        uses capacity;
                        description "An optimistic view of the capacity of the TopologicalEntity assuming that any shared capacity is available to be taken.";
                    }
                    container available-capacity {
                        uses capacity;
                        description "Capacity available to be assigned.";
                    }
                    list capacity-assigned-to-user-view {
                        uses capacity;
                        description "Capacity already assigned";
                    }
                    leaf capacity-interaction-algorithm {
                        type string;
                        description "A reference to an algorithm that describes how various chunks of allocated capacity interact (e.g. when shared)";
                    }
                    description "The TopologicalEntity derives capacity from the underlying realization. 
                        A TopologicalEntity may be an abstraction and virtualization of a subset of the underlying capability offered in a view or may be directly reflecting the underlying realization.
                        A TopologicalEntity may be directly used in the view or may be assigned to another view for use.
                        The clients supported by a multi-layer TopologicalEntity may interact such that the resources used by one client may impact those available to another. This is derived from the LTP spec details.
                        Represents the capacity available to user (client) along with client interaction and usage. 
                        A TopologicalEntity may reflect one or more client protocols and one or more members for each profile.";
                }
                grouping topological-entity {
                    container risk-parameter-pac {
                        if-feature Present if risk information is relevant to usage and statement can be made that applies equally to all flows that can be supported by the TopologicalEntity.
Note that if risk is relevant but consistent ststement cannot be made then the TopologicalEntity should be described in terms of subordinate parts against which coherent statements can be made.;
                        uses risk-parameter-pac;
                        description "none";
                    }
                    container transfer-cost-pac {
                        if-feature Present if cost information is relevant to usage and statement can be made that applies equally to all flows that can be supported by the TopologicalEntity.
Note that if cost is relevant but consistent ststement cannot be made then the TopologicalEntity should be described in terms of subordinate parts against which coherent statements can be made.;
                        uses transfer-cost-pac;
                        description "none";
                    }
                    container transfer-timing-pac {
                        if-feature Present if transfer timing information is relevant to usage and statement can be made that applies equally to all flows that can be supported by the TopologicalEntity.
Note that if transfer timing is relevant but consistent ststement cannot be made then the TopologicalEntity should be described in terms of subordinate parts against which coherent statements can be made.;
                        uses transfer-timing-pac;
                        description "none";
                    }
                    container transfer-capacity-pac {
                        if-feature Present if transfer capacity information is relevant to usage and statement can be made that applies equally to all flows that can be supported by the TopologicalEntity.
Note that if transfer capacity is relevant but consistent ststement cannot be made then the TopologicalEntity should be described in terms of subordinate parts against which coherent statements can be made.;
                        uses transfer-capacity-pac;
                        description "none";
                    }
                    container transfer-integrity-pac {
                        if-feature Present if transfer integrity information is relevant to usage and statement can be made that applies equally to all flows that can be supported by the TopologicalEntity.
Note that if transfer integrity is relevant but consistent ststement cannot be made then the TopologicalEntity should be described in terms of subordinate parts against which coherent statements can be made.;
                        uses transfer-integrity-pac;
                        description "none";
                    }
                    container validation-pac {
                        if-feature Present if validation information is relevant to usage and statement can be made that applies equally to all flows that can be supported by the TopologicalEntity.
Note that if validation is relevant but consistent ststement cannot be made then the TopologicalEntity should be described in terms of subordinate parts against which coherent statements can be made.
Note that validation may not be possible for the specific layer protocol or in the particular case.;
                        uses validation-pac;
                        description "none";
                    }
                    list layer-transition-pac {
                        if-feature Present if layer transition information is relevant to usage and statement can be made that applies equally to all flows that can be supported by the TopologicalEntity.
Note that if layer transiotio is relevant but consistent ststement cannot be made then the TopologicalEntity should be described in terms of subordinate parts against which coherent statements can be made.
Note that layer transition occurs in a limited number of cases.;
                        uses layer-protocol-transition-pac;
                        description "none";
                    }
                    description "A TopologicalEntity is an abstract representation of the emergent effect of the combined functioning of an arrangement of components (running hardware, software running on hardware etc). 
                        The effect can be considered as the realization of the potential for apparent communication adjacency for entities that are bound to the terminations at the boundary of the TopologicalEntity.
                        The TopologicalEntity enables the creation of constrained forwarding to achieve the apparent adjacency.
                        The apparent adjacency has intended performance degraded from perfect adjacency and a statement of that degradation is conveyed via the attributes of the packages associated with this class.
                        In the model both ForwardingDomain and Link are TopologicalEntities. 
                        This abstract class is used as a modeling approach to apply packages of attributes to both Link and ForwardingDomain. Link and ForwardingDomain are the key TopologicalEntities.";
                }
                grouping validation-pac {
                    list validation-mechanism-list {
                        min-elements 1;
                        uses validation-mechanism;
                        description "Provides details of the specific validation mechanism(s) used to confirm the presence of an intended topologicalEntity.";
                    }
                    description "Validation covers the various adjacenct discovery and reachability verification protocols. Also may cover Information source and degree of integrity.";
                }
                feature Present if jitterCharacteristics information is relevant to usage and statement can be made that applies equally to all flows that can be supported by the TopologicalEntity.
Note that if jitterCharacteristics is relevant but consistent ststement cannot be made then the TopologicalEntity should be described in terms of subordinate parts against which coherent statements can be made.
Note that this only applies to TDM. {
                    description "none";
                }
                feature Present if wanderCharacteristics information is relevant to usage and statement can be made that applies equally to all flows that can be supported by the TopologicalEntity.
Note that if wanderCharacteristics is relevant but consistent ststement cannot be made then the TopologicalEntity should be described in terms of subordinate parts against which coherent statements can be made.
Note that this only applies to TDM. {
                    description "none";
                }
                feature Present if queuingLatencyCharacteristics information is relevant to usage and statement can be made that applies equally to all flows that can be supported by the TopologicalEntity.
There may be more than one instance if the queuing behavior depends upon traffic properties.
Note that if queuingLatencyCharacteristics is relevant but consistent statement cannot be made then the TopologicalEntity should be described in terms of subordinate parts against which coherent statements can be made.
Note that this only applies to packet system. {
                    description "none";
                }
                feature Present if errorCharacteristics information is relevant to usage and statement can be made that applies equally to all flows that can be supported by the TopologicalEntity.
Note that if errorCharacteristics is relevant but consistent ststement cannot be made then the TopologicalEntity should be described in terms of subordinate parts against which coherent statements can be made.
Note that this only applies to TDM. {
                    description "none";
                }
                feature Present if lossCharacteristics information is relevant to usage and statement can be made that applies equally to all flows that can be supported by the TopologicalEntity.
Note that if lossCharacteristics is relevant but consistent ststement cannot be made then the TopologicalEntity should be described in terms of subordinate parts against which coherent statements can be made.
Note that this only applies to packet systems. {
                    description "none";
                }
                feature Present if repeatCharacteristics information is relevant to usage and statement can be made that applies equally to all flows that can be supported by the TopologicalEntity.
Note that if repeatCharacteristics is relevant but consistent ststement cannot be made then the TopologicalEntity should be described in terms of subordinate parts against which coherent statements can be made.
Note that this primarily applies to packet systemswhere a packet may be delivered more than once (in fault recovery for example). 
Note that it can also apply to TDM where several frames may  be received twice due to switching in a system with a large differential propagation delay. {
                    description "none";
                }
                feature Present if deliveryOrderCharacteristics information is relevant to usage and statement can be made that applies equally to all flows that can be supported by the TopologicalEntity.
Note that if deliveryOrderCharacteristics is relevant but consistent ststement cannot be made then the TopologicalEntity should be described in terms of subordinate parts against which coherent statements can be made.
Note that this only applies to packet systems.
 {
                    description "none";
                }
                feature Present if serverIntegrityProcessCharacteristics information is relevant to usage and statement can be made that applies equally to all flows that can be supported by the TopologicalEntity.
Note that if serverIntegrityProcessCharacteristics is relevant but consistent ststement cannot be made then the TopologicalEntity should be described in terms of subordinate parts against which coherent statements can be made.
Note that this only applies where the server has some error recovery mechanism alters the characteristics of the link from a normal distribution. {
                    description "none";
                }
                feature Present if risk information is relevant to usage and statement can be made that applies equally to all flows that can be supported by the TopologicalEntity.
Note that if risk is relevant but consistent ststement cannot be made then the TopologicalEntity should be described in terms of subordinate parts against which coherent statements can be made. {
                    description "none";
                }
                feature Present if cost information is relevant to usage and statement can be made that applies equally to all flows that can be supported by the TopologicalEntity.
Note that if cost is relevant but consistent ststement cannot be made then the TopologicalEntity should be described in terms of subordinate parts against which coherent statements can be made. {
                    description "none";
                }
                feature Present if transfer timing information is relevant to usage and statement can be made that applies equally to all flows that can be supported by the TopologicalEntity.
Note that if transfer timing is relevant but consistent ststement cannot be made then the TopologicalEntity should be described in terms of subordinate parts against which coherent statements can be made. {
                    description "none";
                }
                feature Present if transfer capacity information is relevant to usage and statement can be made that applies equally to all flows that can be supported by the TopologicalEntity.
Note that if transfer capacity is relevant but consistent ststement cannot be made then the TopologicalEntity should be described in terms of subordinate parts against which coherent statements can be made. {
                    description "none";
                }
                feature Present if transfer integrity information is relevant to usage and statement can be made that applies equally to all flows that can be supported by the TopologicalEntity.
Note that if transfer integrity is relevant but consistent ststement cannot be made then the TopologicalEntity should be described in terms of subordinate parts against which coherent statements can be made. {
                    description "none";
                }
                feature Present if validation information is relevant to usage and statement can be made that applies equally to all flows that can be supported by the TopologicalEntity.
Note that if validation is relevant but consistent ststement cannot be made then the TopologicalEntity should be described in terms of subordinate parts against which coherent statements can be made.
Note that validation may not be possible for the specific layer protocol or in the particular case. {
                    description "none";
                }
                feature Present if layer transition information is relevant to usage and statement can be made that applies equally to all flows that can be supported by the TopologicalEntity.
Note that if layer transiotio is relevant but consistent ststement cannot be made then the TopologicalEntity should be described in terms of subordinate parts against which coherent statements can be made.
Note that layer transition occurs in a limited number of cases. {
                    description "none";
                }

            grouping forwarding-domain {
                leaf-list layer-protocol-name-list {
                    type layer-protocol-name;
                    min-elements 1;
                    description "One or more protocol layers at which the FD represents the opportunity to enable forwarding between LTP that bound it.";
                }
                leaf-list lower-level-fd-ref-list {
                    type leafref {
                        path '/core-model:network-control-domain/core-model:network-element-ref-list/core-model:fd-ref-list/';
                    }
                    description "The FD object class supports a recursive aggregation relationship (HigherLevelFdEncompassesLowerLevelFds) such that the internal construction of an FD can be exposed as multiple lower level FDs and associated Links (partitioning).
                        The aggregated FDs and Links form an interconnected topology that provides and describes the capability of the aggregating FD.
                        Note that the model actually represents aggregation of lower level FDs into higher level FDs as views rather than FD partition, and supports multiple views. 
                        Aggregation allow reallocation of capacity from lower level FDs to different higher level FDs as if the network is reorganized  (as the association is aggregation not composition).";
                }
                leaf-list fc-ref-list {
                    type leafref {
                        path '/core-model:fc-route/core-model:fc-list/';
                    }
                    description "An FD contains one or more FCs. A contained FC connects LTPs that bound the FD.";
                }
                leaf-list ltp-ref-list {
                    type leafref {
                        path '/core-model:network-control-domain/core-model:network-element-ref-list/core-model:ltp-ref-list/';
                    }
                    description "An instance of FD is associated with zero or more LTP objects. 
                        The LTPs that bound the FD provide capacity for forwarding.";
                }
                leaf-list link-ref-list {
                    type leafref {
                        path '/core-model:link/';
                    }
                    description "The FD encompasses Links that interconnect lower level FDs and collect links that are wholly within the bounds of the FD.
                        See also _lowerLevelFdRefList.";
                }
                uses global-class;
                uses topological-entity;
                description "The ForwardingDomain (FD) object class models the topological component which represents the opportunity to enable forwarding (of specific transport characteristic information at one or more protocol layers) between points represented by the LTP in the model.
                    The FD object provides the context for instructing the formation, adjustment and removal of FCs and hence offers the potential to enable forwarding. 
                    The LTPs available are those defined at the boundary of the FD.
                    At a lowere level of recursion, an FD (within a network element (NE)) represents a switch matrix (i.e., a fabric). 
                    Note that an NE can encompass multiple switch matrices (FDs) and the FD representing the switch matrix can be further partitioned.
                    ";
            }
            grouping forwarding-construct {
                leaf layer-protocol-name {
                    type layer-protocol-name;
                    description "The layerProtocol at which the FC enables potential for forwarding.";
                }
                leaf-list lower-level-fc-ref-list {
                    type leafref {
                        path '/core-model:fc-route/core-model:fc-list/';
                    }
                    description "An FC object supports a recursive aggregation relationship such that the internal construction of an FC can be exposed as multiple lower level FC objects (partitioning).
                        Aggregation is used as for the FD to allow changes in hierarchy.
                        ";
                }
                list fc-route-ref-list {
                    uses fc-route;
                    description "An FC object can have zero or more routes, each of which is defined as a list of lower level FC objects describing the flow across the network.";
                }
                list fc-port-list {
                    min-elements 2;
                    uses fc-port;
                    description "The association of the FC to LTPs is made via FcPorts (essentially the ports of the FC).";
                }
                list fc-switch-list {
                    uses fc-switch;
                    description "If an FC exposes protection (having two FcPorts that provide alternative identical inputs/outputs), the FC will have one or more associated FcSwitch objects.
                        The arrangement of switches for a particular instance is described by a referenced FcSpec";
                }
                list configuration-and-switch-control-list {
                    uses configuration-and-switch-controller;
                    description "A multi-switch controller encapsulated in the FC.
                        The multi-switch controller coordinates multiple switches in the same FC.";
                }
                leaf fc-spec-ref {
                    type leafref {
                        path '/core-model:configuration-group-spec/core-model:fc-spec/';
                    }
                    description "References the specification that describes the capability and internal structure of of the FC (e.g. The arrangement of switches for a particular instance is described by a referenced FcSpec).
                        The specification allows interpretation of FcPort role and switch configurations etc.";
                }
                leaf forwarding-direction {
                    type forwarding-direction;
                    description "The directionality of the ForwardingConstruct. 
                        Is applicable to simple ForwardingConstructs where all FcPorts are BIDIRECTIONAL (the ForwardingConstruct will be BIDIRECTIONAL) or UNIDIRECTIONAL (the ForwardingConstruct will be UNIDIRECTIONAL). 
                        Is not present in more complex cases.";
                }
                uses global-class;
                description "The ForwardingConstruct (FC) object class models enabled potential for forwarding between two or more LTPs at a particular specific layerProtocol.
                    Like the LTP the FC supports any transport protocol including all circuit and packet forms.
                    It is used to effect forwarding of transport characteristic (layer protocol) information.
                    An FC can be in only one FD.
                    The ForwardingConstruct is a Forwarding entity.
                    At a low level of the recursion, a FC represents a cross-connection within an NE. It may also represent a fragment of a cross-connection under certain circumstances.
                    The FC object can be used to represent many different structures including point-to-point (P2P), point-to-multipoint (P2MP), rooted-multipoint (RMP) and multipoint-to-multipoint (MP2MP) bridge and selector structure for linear, ring or mesh protection schemes.";
            }
            list network-control-domain {
                min-elements 1;
                max-elements 2;
                leaf-list forwarding-domain-ref-list {
                    type leafref {
                        path '/core-model:network-control-domain/core-model:network-element-ref-list/core-model:fd-ref-list/';
                    }
                    description "The FDs accessible via the NCD.";
                }
                leaf-list link-ref-list {
                    type leafref {
                        path '/core-model:link/';
                    }
                    description "The links accessible in the scope of the NCD. 
                        The domain is bounded by off-network links.";
                }
                list network-element-ref-list {
                    uses network-element;
                    description "The network elements within the scope of the NCD where each NE is within one and only one domain.";
                }
                uses global-class;
                description "The Network Control Domain (NCD) object class represents the scope of control that a particular SDN controller has with respect to a particular network, (i.e., encompassing a designated set of interconnected network elements).
                    In the interfaces between SDN controllers where virtualization is necessary, e.g., in client/server SDN controller relationship, the NCD object defines the scope of control of the client SDN controller on the virtual network that has been provided by the server SDN controller (i.e., the scope of control relates to the partitioned provider resources allocated to that particular client). 
                    The NCD provides the scope of naming space for identifying objects representing the virtual resources within the virtual network.";
            }
            grouping link {
                leaf-list layer-protocol-name-list {
                    type layer-protocol-name;
                    min-elements 1;
                    description "The Link can support multiple transport layer protocols via the associated LTP object. 
                        For implementation optimization, where appropriate, multiple layer-specific links can be merged and represented as a single Link instance as the Link can represent a list of layer protocols.
                        A link may support different layer protocols at each Port when it is a transitional link.";
                }
                leaf-list fd-ref-list {
                    type leafref {
                        path '/core-model:network-control-domain/core-model:network-element-ref-list/core-model:fd-ref-list/';
                    }
                    min-elements 2;
                    description "The Link associates with two or more FDs. 
                        This association provides a direct summarization of the association via LinkPort and LTP.";
                }
                list link-port-list {
                    min-elements 2;
                    uses link-port;
                    description "The association of the Link to LTPs is made via LinkPort (essentially the ports of the Link).";
                }
                leaf link-spec-ref {
                    type leafref {
                        path '/core-model:link-spec/';
                    }
                    description "References the specification that describes the capability and internal structure of of the Link (e.g. asymmetric flows between points).
                        The specification allows interpretation of LinkPort role and switch configurations etc.
                        See also ForwardingConstruct.";
                }
                leaf-list aggregated-link {
                    type leafref {
                        path '/core-model:link/';
                    }
                    description "A link may formed from subordinate links (similar FD formations from subordiate FDs). This association is intended to cover concepts such as serial compound links. ";
                }
                leaf link-direction {
                    type forwarding-direction;
                    description "The directionality of the Link. 
                        Is applicable to simple Links where all LinkPorts are BIDIRECTIONAL (the Link will be BIDIRECTIONAL) or UNIDIRECTIONAL (the Link will be UNIDIRECTIONAL). 
                        Is not present in more complex cases.";
                }
                uses global-class;
                uses topological-entity;
                description "The Link object class models effective adjacency between two or more ForwardingDomains (FD). 
                    In its basic form (i.e., point-to-point Link) it associates a set of LTP clients on one FD with an equivalent set of LTP clients on another FD. 
                    Like the FC, the Link has ports (LinkPort) which take roles relevant to the constraints on flows offered by the Link (e.g., Root role or leaf role for a Link that has a constrained Tree configuration). 
                    The Link is a Forwarding entity.";
            }
            grouping network-element {
                list fd-ref-list {
                    uses forwarding-domain;
                    description "Represents the FD that is completely within the boundary of the NE.
                        At a low level of recursion, an FD (within a network element (NE)) represents a switch matrix (i.e., a fabric). 
                        Note that an NE can encompass multiple switch matrices (FDs) and the FD representing the switch matrix can be further partitioned.
                        Where an FD is referenced by the NeEncompassesFd association, any FDs that it encompasses (i.e., that are associated with it by HigherLevelFdEncompassesLowerLevelFds), must also be encompassed by the NE and hence must have the NeEncompassesFd association.
                        ";
                }
                leaf-list ltpp-list {
                    type string;
                    description "OBSOLETE. Was reference to LtpPool. The pool has now been subsumed into the LTP.
                        This will be deleted in the next release.";
                }
                list ltp-ref-list {
                    uses logical-termination-point;
                    description "An NE has associated LTPs that are at its boundary.
                        The NeEncompassesFd association occurs for FDs that are within the bounds of the NetworkElement definition such that the FD is bounded by LTPs, all of which are on the boundary of the NetworkElement or are within the NetworkElement. 
                        An LTP can be independent of an NE.";
                }
                uses global-class;
                description "The Network Element (NE) object class represents a network element (traditional NE) in the data plane.
                    A data plane network element is essentially a consolidation of capabilities that can be viewed and controlled through a 'single' management-control port.
                    In the direct interface from an SDN controller to a network element in the data plane, the NetworkElement object defines the scope of control for the resources within the network element
                    For example internal transfer of user information between the external terminations (ports of the NE), encapsulation, multiplexing/demultiplexing, and OAM functions, etc. 
                    The NetworkElement provides the scope of the naming space for identifying objects representing the resources within the data plane network element.
                    NE is really a product bundling or some view of management scope, management access, session. 
                    The NE is not directly part of topology but brings meaning to the FD context and the LTP context (and hence the links). ";
            }
            grouping sdn-controller {
                uses global-class;
                description "Represents the SDN controller.";
            }
            grouping fc-port {
                leaf-list ltp-ref-list {
                    type leafref {
                        path '/core-model:network-control-domain/core-model:network-element-ref-list/core-model:ltp-ref-list/';
                    }
                    max-elements 2;
                    description "The FcPort may be associated with more than one LTP when the FcPort is bidirectional and the LTPs are unidirectional.
                        Multiple Ltp
                        - Bidirectional FcPort to two Uni Ltps
                        Zero Ltp
                        - BreakBeforeMake transition
                        - Planned Ltp not yet in place
                        - Off-network LTP referenced through other mechanism";
                }
                leaf role {
                    type port-role;
                    description "Each FcPort of the FC has a role (e.g., working, protection, protected, symmetric, hub, spoke, leaf, root)  in the context of the FC with respect to the FC function. ";
                }
                leaf fc-port-direction {
                    type port-direction;
                    description "The orientation of defined flow at the FcPort.";
                }
                uses local-class;
                description "The association of the FC to LTPs is made via FcPorts.
                    The FcPort object class models the access to the FC function. 
                    The traffic forwarding between the associated FcPorts of the FC depends upon the type of FC and may be associated with FcSwitch object instances.  
                    In cases where there is resilience the FcPort may convey the resilience role of the access to the FC. 
                    It can represent a protected (resilient/reliable) point or a protecting (unreliable working or protection) point.
                    The FcPort replaces the Protection Unit of a traditional protection model. 
                    The ForwadingConstruct can be considered as a component and the FcPort as a Port on that component";
            }
            grouping layer-protocol {
                leaf layer-protocol-name {
                    type layer-protocol-name;
                    description "Indicate the specific layer-protocol described by the LayerProtocol entity.";
                }
                leaf lp-spec {
                    type leafref {
                        path '/core-model:lp-spec/';
                    }
                    description "The LpSpec identifies the interna structure of the LP explaining internal flexibilities, degree of termination and degree of adaptation on both client and server side.";
                }
                leaf configured-client-capacity {
                    type string;
                    description "Provides a summarized view of the client capacity that is configurable for use.
                        Note the cleint LTP association should provide all necessary detail hence this attribute is questionable.";
                }
                leaf lp-direction {
                    type termination-direction;
                    description "The overall directionality of the LP. 
                        - A BIDIRECTIONAL LP will have some SINK and/or SOURCE flowss.
                        - A SINK LP can only contain elements with SINK flows or CONTRA_DIRECTION_SOURCE flows
                        - A SOURCE LP can only contain SOURCE flows or CONTRA_DIRECTION_SINK flows";
                }
                leaf termination-state {
                    type string;
                    description "Indicates whether the layer is terminated and if so how.";
                }
                uses local-class;
                description "Each transport layer is represented by a LayerProtocol (LP) instance. The LayerProtocol instances it can be used for controlling termination and monitoring functionality. 
                    It can also be used for controlling the adaptation (i.e. encapsulation and/or multiplexing of client signal), tandem connection monitoring, traffic conditioning and/or shaping functionality at an intermediate point along a connection. 
                    Where the client – server relationship is fixed 1:1 and immutable, the layers can be encapsulated in a single LTP instance. Where the is a n:1 relationship between client and server, the layers must be split over two separate instances of LTP. ";
            }
            grouping logical-termination-point {
                leaf-list server-ltp-ref-list {
                    type leafref {
                        path '/core-model:network-control-domain/core-model:network-element-ref-list/core-model:ltp-ref-list/';
                    }
                    description "References contained LTPs representing servers of this LTP in an inverse multiplexing configuration (e.g. VCAT).";
                }
                leaf-list client-ltp-ref-list {
                    type leafref {
                        path '/core-model:network-control-domain/core-model:network-element-ref-list/core-model:ltp-ref-list/';
                    }
                    description "References contained LTPs representing client traffic of this LTP for normal cases of multiplexing.";
                }
                list lp-list {
                    min-elements 1;
                    uses layer-protocol;
                    description "Ordered list of LayerProtocols that this LTP is comprised of where the first entry in the list is the lowest server layer (e.g. physical)";
                }
                leaf connected-ltp-ref {
                    type leafref {
                        path '/core-model:network-control-domain/core-model:network-element-ref-list/core-model:ltp-ref-list/';
                    }
                    description "Applicable in a simple context where two LTPs are associated via a non-adjustable enabled forwarding.
                        Reduces clutter removing the need for two additional LTPs and an FC with a pair of FcPorts.";
                }
                leaf peer-ltp-ref {
                    type leafref {
                        path '/core-model:network-control-domain/core-model:network-element-ref-list/core-model:ltp-ref-list/';
                    }
                    description "References contained LTPs representing the reversal of orientation of flow where two LTPs are associated via a non-adjustable enabled forwarding and where the referenced LTP is fully dependent on the this LTP.";
                }
                leaf ltp-spec {
                    type leafref {
                        path '/core-model:ltp-spec/';
                    }
                    description "The specification of the LTP defines internal structure of the LTP.
                        The specification allows interpretation of organisatoon of LPs making up the LTP and also identifies which inter-LTP associations are valid.";
                }
                leaf-list physical-port-reference {
                    type string;
                    description "One or more text labels for the unmodelled physical port associated with the LTP.
                        In many cases there is no associated physical port";
                }
                leaf-list ltp-ref-list {
                    type leafref {
                        path '/core-model:network-control-domain/core-model:network-element-ref-list/core-model:ltp-ref-list/';
                    }
                    description "References one or more LTPs in other views that represent this LTP. 
                        The referencing LTP is the rovider of capability.";
                }
                leaf ltp-direction {
                    type termination-direction;
                    description "The overall directionality of the LTP. 
                        - A BIDIRECTIONAL LTP must have at least some LPs that are BIDIRECTIONAL but may also have some SINK and/or SOURCE LPs.
                        - A SINK LTP can only contain SINK LPs
                        - A SOURCE LTP can only contain SOURCE LPs";
                }
                uses global-class;
                description "The LogicalTerminationPoint (LTP) object class encapsulates the termination and adaptation functions of one or more transport layers. 
                    The structure of LTP supports all transport protocols including circuit and packet forms.";
            }
            grouping fc-route {
                list fc-list {
                    min-elements 2;
                    uses forwarding-construct;
                    description "The list of FCs describing the route of an FC.";
                }
                uses local-class;
                description "The FC Route (FcRoute) object class models the individual routes of an FC. The route is an alternative view of the internal structure of the FC.
                    The route of an FC object is represented by a list of FCs at a lower level with the implicit understanding that unmodelled link connections are interleaved between the lower level FCs. 
                    Note that depending on the service supported by an FC, an the FC can have multiple routes.
                    Also applicable where NE level ForwardingDomain may be decomposed into subordinate ForwardingDomains. Applies to both virtual and real NE cases.";
            }
            grouping fc-switch {
                leaf hold-off-time {
                    type uint64;
                    description "This attribute indicates the time, in seconds, between declaration of unacceptable quality of signal on the currently selected FcPort, and the initialization of the protection switching algorithm. ";
                }
                leaf wait-to-restore-time {
                    type uint64;
                    description "If the protection system is revertive, this attribute specifies the amount of time, in seconds, to wait after the preferred FcPort returns to an acceptable state of operaion (e.g a fault has cleared) before restoring traffic to that preferred FcPort. ";
                }
                leaf prot-type {
                    type protection-type;
                    description "Indicates the protection scheme that is used for the ProtectionGroup.";
                }
                leaf oper-type {
                    type oper-type;
                    description "This attribute whether or not the protection scheme is revertive or non-revertive. ";
                }
                leaf-list selected-fc-port-ref-list {
                    type leafref {
                        path '/core-model:fc-route/core-model:fc-list/core-model:fc-port-list/';
                    }
                    min-elements 1;
                    description "Indicates which points are selected by the switch.";
                }
                leaf-list profile-proxy-ref-list {
                    type leafref {
                        path '/core-model:profile-proxy/';
                    }
                    description "Provides a set of predefined values for switch control in place of the direct values avaiable via the FcSwitch or via _configurationAndSwitchControl ";
                }
                leaf configuration-and-switch-control-ref {
                    type leafref {
                        path '/core-model:fc-route/core-model:fc-list/core-model:configuration-and-switch-control-list/';
                    }
                    description "A multi-switch controller external to the FcSwitch.
                        The multi-switch controller coordinates multiple switches in the same FC or across multple FCs";
                }
                container configuration-and-switch-control {
                    uses configuration-and-switch-controller;
                    description "A switch controller encapsulated in the FcSwitch.
                        ";
                }
                uses local-class;
                description "none";
            }
            grouping link-port {
                leaf ltpp {
                    type string;
                    description "OBSOLETE. Was reference to LtpPool. The pool has now been subsumed into the LTP.
                        This will be deleted in the next release.";
                }
                leaf-list ltp-ref-list {
                    type leafref {
                        path '/core-model:network-control-domain/core-model:network-element-ref-list/core-model:ltp-ref-list/';
                    }
                    description "The LinkPort may be associated with more than one LTP when the LinkPort is bidirectional and the LTPs are unidirectional.
                        Multiple Ltp
                        - Bidirectional LinkPort to two Uni Ltps
                        Zero Ltp
                        - BreakBeforeMake transition
                        - Planned Ltp not yet in place
                        - Off-network LTP referenced through other mechanism";
                }
                leaf role {
                    type port-role;
                    description "Each LinkPort of the Link has a role (e.g., symmetric, hub, spoke, leaf, root)  in the context of the Link with respect to the Link function. ";
                }
                leaf off-network-address {
                    type string;
                    description "A freeform opportunity to express a reference for an Port of the Link that is not outside the scope of the control domain.
                        This attribute is expected to convey a foreign identifier/name/address or a shared reference for some mid-span point at the boundary between two administrative domains.
                        This attribute is used when an LTP cannot be referenced.";
                }
                leaf link-port-direction {
                    type port-direction;
                    description "The orientation of defined flow at the LinkPort.";
                }
                uses local-class;
                description "none";
            }

        /***********************
        * package diagrams
        **********************/ 

        /***********************
        * package associations
        **********************/ 


    /***********************
    * package core-foundation-module
    **********************/ 
        /***********************
        * package type-definitions
        **********************/ 
            typedef date-and-time {
                type string;
                description "This primitive type defines the date and time according to the following structure:
                    'yyyyMMddhhmmss.s[Z|{+|-}HHMm]' where:
                    yyyy    '0000'..'9999'    year
                    MM        '01'..'12'            month
                    dd        '01'..'31'            day
                    hh        '00'..'23'            hour
                    mm        '00'..'59'            minute
                    ss        '00'..'59'            second
                    s        '.0'..'.9'            tenth of second (set to '.0' if EMS or NE cannot support this granularity)
                    Z        'Z'                    indicates UTC (rather than local time)
                    {+|-}    '+' or '-'            delta from UTC
                    HH        '00'..'23'            time zone difference in hours
                    Mm        '00'..'59'            time zone difference in minutes.";
            }
            typedef bit-string {
                type string;
                description "This primitive type defines a bit oriented string.
                    The size of the BitString will be defined in the valueRange property of the attribute; according to ASN.1 (X.680).
                    The semantic of each bit position will be defined in the Documentation field of the attribute.";
            }
            typedef real {
                type string;
                description "This primitive type maps to the 'realnumber' defined in Recommendation X.680.";
            }
            typedef printable-string {
                type string;
                description "A string that only includes printable characters";
            }

        /***********************
        * package super-classes-and-common-packages
        **********************/ 
            /***********************
            * package object-classes
            **********************/ 
                grouping name {
                    list name-list {
                        min-elements 1;
                        uses name-and-value;
                        description "List of names.";
                    }
                    description "Name: A property of an entity with a value that is unique in some namespace but may change during the life of the entity. A name carries no semantics with respect to the purpose of the entity.";
                }
                grouping global-class {
                    list local-id-list {
                        uses name-and-value;
                        description "An identifier that is unique in the context of some scope that is less than the global scope.
                            (consider in the context of Identifier: A property of an entity/role with a value that is unique within an identifier space, where the identifier space is itself unique, and immutable. The identifier therefore represents the identity of the entity/role. An identifier carries no semantics with respect to the purpose of the entity.)";
                    }
                    leaf uuid {
                        type universal-id;
                        description "UUID: An identifier that is universally unique
                            (consider in the context of Identifier: A property of an entity/role with a value that is unique within an identifier space, where the identifier space is itself globally unique, and immutable. An identifier carries no semantics with respect to the purpose or state of the entity)";
                    }
                    uses name;
                    uses label;
                    uses extension;
                    uses state-pac;
                    description "Represents a type of thing (an Entity) that has instances which can exist in their own right (independently of any others).
                        Entity: Has identity, defined boundary, properties, functionality and lifecycle in a global context.
                        (consider in the context of an Object Class: (usage) The representation of a thing that may be an entity or an inseparable Entity Feature)";
                }
                grouping local-class {
                    list local-id-list {
                        min-elements 1;
                        uses name-and-value;
                        description "An identifier that is unique in the context of some scope that is less than the global scope.
                            (consider in the context of Identifier: A property of an entity/role with a value that is unique within an identifier space, where the identifier space is itself unique, and immutable. The identifier therefore represents the identity of the entity/role. An identifier carries no semantics with respect to the purpose of the entity.)";
                    }
                    uses name;
                    uses label;
                    uses extension;
                    uses state-pac;
                    description "A LocalClass represents a Feature of an Entity. It is inseparable from a GlobalClass but is a distinct feature of that GlobalClass such that the instances of LocalClass are able to have associations to other instances..
                        Feature of an Entity: An inseparable, externally distinguishable part of an entity.
                        The mandatory LocalId of the LocalClass instance is unique in the context of the GlobalClass from which it is inseparable.
                        (consider in the context of an Object Class: (usage) The representation of a thing that may be an entity or an inseparable feature of an entity)
                        ";
                }
                grouping label {
                    list label-list {
                        uses name-and-value;
                        description "List of labels.";
                    }
                    description "A property of an entity with a value that is not expected to be unique and is allowed to change. A label carries no semantics with respect to the purpose of the entity and has no effect on the entity behavior or state.";
                }
                grouping extension {
                    list extension-list {
                        uses name-and-value;
                        description "List of simple name-value extentions";
                    }
                    description "Extension provides an opportunity to define properties not declared in the class that extend the class enabling a realization with simple ad-hoc extension of standard classes to be conformant.";
                }
                grouping universal-id-authority {
                    leaf uuid {
                        type universal-id;
                        description "The UUID for the UUID authority.";
                    }
                    description "Represents the authority that controls the allocation of UUIDs.";
                }
                grouping name-and-value-authority {
                    leaf uuid {
                        type universal-id;
                        description "The UUID for the NameValueAuthority.";
                    }
                    description "Represents the authority that controls the legal valuse for the names and values of a name/value attribute.";
                }
                grouping conditional-package {
                    uses extension;
                    uses label;
                    description "The base class for conditional packages.";
                }

            /***********************
            * package type-definitions
            **********************/ 
                grouping name-and-value {
                    leaf value-name {
                        type string;
                        description "The name of the value. The value need not have a name.";
                    }
                    leaf value {
                        type string;
                        description "The value";
                    }
                    leaf name-and-value-authority-ref {
                        type leafref {
                            path '/core-model:name-and-value-authority/';
                        }
                        description "The authority that defines the named value.";
                    }
                    leaf global-class-ref {
                        type leafref {
                            path '/core-model:global-class/';
                        }
                        description "The scope of the name uniqueness";
                    }
                    leaf local-class-ref {
                        type leafref {
                            path '/core-model:local-class/';
                        }
                        description "The scope of the name uniqueness";
                    }
                    description "A scoped name-value pair";
                }
                typedef universal-id {
                    type string;
                    description "The univeral ID value where the mechanism for generation is defned by some authority not directly referenced in the structure.";
                }


        /***********************
        * package state-model
        **********************/ 
            /***********************
            * package object-classes
            **********************/ 
                grouping state-pac {
                    leaf operational-state {
                        type operational-state;
                        config false;
                        description "The operational state is used to indicate whether or not the resource is installed and working";
                    }
                    leaf administrative-control {
                        type administrative-control;
                        description "The administrativeControl state provides control of the availability of specific resources without modification to the provisioning of those resources.
                            The value is the current control target. The actual administrativeState may or may not be at target.";
                    }
                    leaf adminsatratve-state {
                        type administrative-state;
                        config false;
                        description "Shows whether or not the client has permission to use or has a prohibition against using the resource.
                            The administrative state expresses usage permissions for specific resources without modification to the provisioning of those resources.";
                    }
                    leaf lifecycle-state {
                        type lifecycle-state;
                        description "Used to track the planned deployment, allocation to clients and withdrawal of resources. ";
                    }
                    description "Provides general state attributes.";
                }

            /***********************
            * package type-definitions
            **********************/ 
                typedef operational-state {
                    type enumeration {
                        enum disabled {
                            description "The resource is unable to meet the SLA of the user of the resource. If no (explicit) SLA is defined the resource is disabled if it is totally inoperable and unable to provide service to the user.";
                        }
                        enum enabled {
                            description "The resource is partially or fully operable and available for use";
                        }
                    }
                    description "The possible values of the operationalState.";
                }
                typedef administrative-state {
                    type enumeration {
                        enum locked {
                            description "Users are administratively prohibited from making use of the resource.";
                        }
                        enum unlocked {
                            description "Users are allowed to use the resource";
                        }
                    }
                    description "The possible values of the administrativeState.";
                }
                typedef administrative-control {
                    type enumeration {
                        enum unlock {
                            description "The intention is for the entity to become unlocked.
                                The entity may already be UNLOCKED.";
                        }
                        enum lock-passive {
                            description "The intention is for the entity to become locked but no effort is expected to move to the Locked state (the state will be achieved once all users stop using the resource). 
                                The entity may be LOCKED";
                        }
                        enum lock-active {
                            description "The intention is for the entity to become locked and it is expected that effort will be made to move to the Locked state (users will be actively removed). 
                                The entity may already be LOCKED.";
                        }
                        enum lock-immediate {
                            description "The intention is for the entity to become locked and it is expected to move to the Locked state immediately (users will be force removed). 
                                The entity may already be LOCKED.";
                        }
                    }
                    description "Reflects the current control action when the entity is not in the desired state.
                        The possible values of the current target administrative state.";
                }
                typedef extended-admin-state {
                    type enumeration {
                        enum locked {
                            description "Users are administratively prohibited from making use of the resource.";
                        }
                        enum unlocked {
                            description "Users are allowed to use the resource";
                        }
                        enum shutting-down-active {
                            description "The entity is administratively restricted to existing instances of use only. There are specific actions to remove existing uses. There may be no new instances of use enabled. This corresponds to a control of LOCK_ACTIVE.";
                        }
                        enum shutting-down-passive {
                            description "The entity is administratively restricted to existing instances of use only. There may be no new instances of use enabled. This corresponds to a control of LOCK_PASSIVE.";
                        }
                    }
                    description "Possible extentions to AdministrativeState";
                }
                typedef lifecycle-state {
                    type enumeration {
                        enum planned {
                            description "The resource is planned but is not present in the network.";
                        }
                        enum potential {
                            description "The supporting resources are present in the network but are shared with other clients; or require further configuration before they can be used; or both.
                                o    When a potential resource is configured and allocated to a client it is moved to the “installed” state for that client.
                                o    If the potential resource has been consumed (e.g. allocated to another client) it is moved to the “planned” state for all other clients.";
                        }
                        enum installed {
                            description "The resource is present in the network and is capable of providing the service expected.";
                        }
                        enum pending-removal {
                            description "The resource has been marked for removal";
                        }
                    }
                    description "The possible values of the lifecycleState.";
                }



    /***********************
    * package core-model-enhancements
    **********************/ 
        /***********************
        * package fc-switch-enhancements-developed
        **********************/ 
            grouping profile-proxy {
                leaf profile-proxy-mode {
                    type string;
                    description "A parameter profile may be used in a number of different ways:
                        - Forces the values on the target with no opportunity to see or override the values in the target
                        - Sets the values on the target that can be seen on the target
                        - Sets the values on the target and supports override on the target so the target can be set away from the value in the profile
                        - etc";
                }
                container control-parameters {
                    uses control-parameters;
                    description "The control parameters that can be set int the profile and applied to the target.
                        Not all parameters need be selected and applied.";
                }
                description "A lightweight sketch placeholder for the profile model.";
            }
            grouping configuration-and-switch-controller {
                leaf swich-rule {
                    type string;
                    description "A sketch of the presence of complex rules governing the switch behavior.";
                }
                leaf-list fc-switch-ref-list {
                    type leafref {
                        path '/core-model:fc-route/core-model:fc-list/core-model:fc-switch-list/';
                    }
                    description "The switch being controlled.";
                }
                container control-parameters {
                    uses control-parameters;
                    description "The control parameters to be aplied if local parameters are used rather than profiles";
                }
                leaf-list profile-proxy-ref {
                    type leafref {
                        path '/core-model:profile-proxy/';
                    }
                    description "Applied profiles.";
                }
                description "Sketch representation of a cntroller with basic capability to control switched and add/delete/modify FCs.";
            }
            grouping control-parameters {
                leaf oper-type {
                    type oper-type;
                    description "This attribute whether or not the protection scheme is revertive or non-revertive. ";
                }
                leaf wait-to-restore-time {
                    type uint64;
                    description "If the protection system is revertive, this attribute specifies the amount of time, in seconds, to wait after a fault clears before restoring traffic to the protected protectionUnit that initiated the switching. Valid values for this attribute are integers.";
                }
                leaf prot-type {
                    type protection-type;
                    description "Indicates the protection scheme that is used for the ProtectionGroup.";
                }
                leaf hold-off-time {
                    type uint64;
                    description "This attribute indicates the time, in seconds, between declaration of signal degrade or signal fail, and the initialization of the protection switching algorithm. Valid values are integers in units of seconds.";
                }
                description "A list of control parameters to apply to a switch";
            }
            container configuration-group {
                list configuration-and-switch-control-ref-list {
                    uses configuration-and-switch-controller;
                    description "A controller operating in the scope defined.";
                }
                description "Represents a scope of control for one or more Controllers";
            }

        /***********************
        * package profiles-templates-and-specifications-module
        **********************/ 
            /***********************
            * package fc-capability-developed
            **********************/ 
                /***********************
                * package object-classes
                **********************/ 
                    grouping multi-switched-uni-flow {
                        list ingress-fc-port {
                            min-elements 1;
                            uses ingress-fc-port-set;
                            description "none";
                        }
                        list egress-fc-port {
                            min-elements 1;
                            uses egress-fc-port-set;
                            description "none";
                        }
                        container switch-control {
                            uses configuration-and-switch-control;
                            description "none";
                        }
                        leaf ingress-fc-port-set {
                            type leafref {
                                path '/core-model:configuration-group-spec/core-model:fc-spec/core-model:multi-switched-uni-flow/core-model:ingress-fc-port/';
                            }
                            description "none";
                        }
                        leaf egress-fc-port-set {
                            type leafref {
                                path '/core-model:configuration-group-spec/core-model:fc-spec/core-model:multi-switched-uni-flow/core-model:egress-fc-port/';
                            }
                            description "none";
                        }
                        uses local-class;
                        description "none";
                    }
                    grouping ingress-fc-port-set {
                        uses local-class;
                        description "none";
                    }
                    grouping egress-fc-port-set {
                        uses local-class;
                        description "none";
                    }
                    grouping configuration-and-switch-control {
                        list switch-control-rule {
                            min-elements 1;
                            uses control-rule;
                            description "none";
                        }
                        leaf-list switch {
                            type string;
                            min-elements 1;
                            description "none";
                        }
                        leaf-list egress-selection {
                            type string;
                            min-elements 1;
                            description "none";
                        }
                        uses global-class;
                        description "none";
                    }
                    grouping fc-spec {
                        list multi-switched-uni-flow {
                            min-elements 1;
                            uses multi-switched-uni-flow;
                            description "none";
                        }
                        list switch-control {
                            uses configuration-and-switch-control;
                            description "none";
                        }
                        list fc-port-spec {
                            min-elements 1;
                            uses fc-port-set-spec;
                            description "none";
                        }
                        leaf fc-switch-group-spec {
                            type leafref {
                                path '/core-model:configuration-group-spec/';
                            }
                            description "none";
                        }
                        container ltp-association-rule {
                            uses ltp-association-rule;
                            description "none";
                        }
                        uses global-class;
                        description "none";
                    }
                    grouping configuration-group-spec {
                        container switch-control {
                            uses configuration-and-switch-control;
                            description "none";
                        }
                        container fc-spec {
                            uses fc-spec;
                            description "none";
                        }
                        container ltp-association-rule {
                            uses ltp-association-rule;
                            description "none";
                        }
                        uses global-class;
                        description "none";
                    }
                    grouping control-rule {
                        leaf switch-control-switch-1 {
                            type string;
                            description "none";
                        }
                        uses local-class;
                        description "none";
                    }
                    grouping fc-port-set-spec {
                        leaf-list ingress-fc-port-set {
                            type leafref {
                                path '/core-model:configuration-group-spec/core-model:fc-spec/core-model:multi-switched-uni-flow/core-model:ingress-fc-port/';
                            }
                            description "none";
                        }
                        leaf-list egress-fc-port-set {
                            type leafref {
                                path '/core-model:configuration-group-spec/core-model:fc-spec/core-model:multi-switched-uni-flow/core-model:egress-fc-port/';
                            }
                            description "none";
                        }
                        leaf ltp-association-rule {
                            type leafref {
                                path '/core-model:configuration-group-spec/core-model:fc-spec/core-model:ltp-association-rule/';
                            }
                            description "none";
                        }
                        leaf role {
                            type string;
                            default "true";
                            description "none";
                        }
                        uses local-class;
                        description "none";
                    }
                    grouping ltp-association-rule {
                        uses local-class;
                        description "none";
                    }
                    container switch-property-spec-pac {
                        description "none";
                    }
                    container ingress-fc-port-set-spec-pac {
                        description "none";
                    }


            /***********************
            * package ltp-capability-developed
            **********************/ 
                /***********************
                * package object-classes
                **********************/ 
                    grouping lp-spec {
                        container adapter-spec {
                            uses connection-point-and-adapter-spec;
                            description "none";
                        }
                        container termination-spec {
                            uses termination-spec;
                            description "none";
                        }
                        list adapter-property-spec-list {
                            uses adapter-property-spec;
                            description "none";
                        }
                        container provider-view-spec {
                            uses provider-view-spec;
                            description "none";
                        }
                        list server-spec-list {
                            uses server-spec;
                            description "none";
                        }
                        description "none";
                    }
                    grouping client-spec {
                        leaf-list mapping-interaction-rule-ref-list {
                            type leafref {
                                path '/core-model:lp-spec/core-model:adapter-property-spec-list/core-model:mapping-interaction-rule-list/';
                            }
                            description "none";
                        }
                        description "none";
                    }
                    grouping mapping-interaction-rule {
                        description "none";
                    }
                    grouping termination-spec {
                        container connection-spec {
                            uses connection-spec;
                            description "none";
                        }
                        description "none";
                    }
                    grouping adapter-property-spec {
                        list pool-property-spec-list {
                            uses pool-property-spec;
                            description "none";
                        }
                        leaf-list mapping-interaction-rule-ref-list {
                            type leafref {
                                path '/core-model:lp-spec/core-model:adapter-property-spec-list/core-model:mapping-interaction-rule-list/';
                            }
                            description "none";
                        }
                        list mapping-interaction-rule-list {
                            uses mapping-interaction-rule;
                            description "none";
                        }
                        description "none";
                    }
                    grouping pool-property-spec {
                        container client-spec {
                            uses client-spec;
                            description "none";
                        }
                        leaf client-capacity {
                            type string;
                            default "true";
                            description "none";
                        }
                        leaf-list adapter-property-spec-ref-list {
                            type leafref {
                                path '/core-model:lp-spec/core-model:adapter-property-spec-list/';
                            }
                            description "none";
                        }
                        description "none";
                    }
                    grouping connection-spec {
                        description "none";
                    }
                    grouping connection-point-and-adapter-spec {
                        leaf connection-spec {
                            type leafref {
                                path '/core-model:lp-spec/core-model:termination-spec/core-model:connection-spec/';
                            }
                            description "none";
                        }
                        description "none";
                    }
                    grouping provider-view-spec {
                        leaf-list pool-property-spec-list {
                            type leafref {
                                path '/core-model:lp-spec/core-model:adapter-property-spec-list/core-model:pool-property-spec-list/';
                            }
                            description "none";
                        }
                        description "none";
                    }
                    grouping server-spec {
                        description "none";
                    }
                    grouping ltp-spec {
                        leaf-list lp-spec-list {
                            type leafref {
                                path '/core-model:lp-spec/';
                            }
                            min-elements 1;
                            description "none";
                        }
                        description "none";
                    }


            /***********************
            * package link-capability-sketch
            **********************/ 
                grouping link-spec {
                    description "Describes the capabilities of the Link focussing on link asymmetries and constraints.";
                }

            /***********************
            * package spec-and-profile-sketch
            **********************/ 
                list any-entity-instance {
                    leaf-list profile-ref-list {
                        type leafref {
                            path '/core-model:profile-instance/';
                        }
                        description "none";
                    }
                    leaf spec-ref {
                        type leafref {
                            path '/core-model:spec-instance/';
                        }
                        description "none";
                    }
                    leaf class {
                        type leafref {
                            path '/core-model:any-entity-class/';
                        }
                        description "none";
                    }
                    description "none";
                }
                grouping profile-instance {
                    leaf spec-instance-ref {
                        type leafref {
                            path '/core-model:spec-instance/';
                        }
                        description "none";
                    }
                    leaf profile-class {
                        type leafref {
                            path '/core-model:profile-class/';
                        }
                        description "none";
                    }
                    leaf class {
                        type leafref {
                            path '/core-model:any-entity-class/';
                        }
                        description "none";
                    }
                    description "none";
                }
                grouping spec-instance {
                    leaf spec-class {
                        type leafref {
                            path '/core-model:spec-class/';
                        }
                        description "none";
                    }
                    leaf class-ref {
                        type leafref {
                            path '/core-model:any-entity-class/';
                        }
                        description "none";
                    }
                    description "none";
                }
                grouping any-entity-class {
                    description "none";
                }
                grouping spec-class {
                    uses any-entity-class;
                    description "none";
                }
                grouping profile-class {
                    uses any-entity-class;
                    description "none";
                }


        /***********************
        * package modeling-enhancements
        **********************/ 

        /***********************
        * package view-abstraction-rule-sketch
        **********************/ 
            list view-abstraction-rules {
                leaf-list -ltp-relatest-to-ltp-in-other-view {
                    type string;
                    description "none";
                }
                description "Provides rules and access to policies that govern and explain the view abstraction.
                    At this point it appears that this is not necessary however it has been left in the model as there is still some view abstraction work to be done.";
            }

        /***********************
        * package information-architecture-and-patterns
        **********************/ 
            /***********************
            * package essential-structure-sketch
            **********************/ 
                grouping component {
                    list port {
                        min-elements 1;
                        uses port;
                        description "none";
                    }
                    list attribute-package-list {
                        uses attribute-package;
                        description "none";
                    }
                    leaf bound-component {
                        type leafref {
                            path '/core-model:component/';
                        }
                        description "none";
                    }
                    leaf encapsulated-system {
                        type leafref {
                            path '/core-model:system/';
                        }
                        description "none";
                    }
                    description "none";
                }
                grouping port {
                    leaf role {
                        type string;
                        default "true";
                        description "none";
                    }
                    leaf bound-port {
                        type leafref {
                            path '/core-model:component/core-model:port/';
                        }
                        description "none";
                    }
                    description "none";
                }
                grouping system {
                    description "none";
                }
                grouping attribute-package {
                    description "none";
                }


        /***********************
        * package inter-view-relationships-sketch
        **********************/ 
            grouping sketch-fc {
                leaf supporting-fc-in-other-view-ref {
                    type leafref {
                        path '/core-model:sketch-fc/';
                    }
                    description "none";
                }
                leaf-list suported-fc-in-other-view {
                    type leafref {
                        path '/core-model:sketch-fc/';
                    }
                    description "none";
                }
                description "none";
            }
            grouping sketch-ltp {
                leaf supporting-ltp-in-other-view-ref {
                    type leafref {
                        path '/core-model:sketch-ltp/';
                    }
                    description "none";
                }
                leaf-list supported-ltp-in-other-view-ref {
                    type leafref {
                        path '/core-model:sketch-ltp/';
                    }
                    description "none";
                }
                description "none";
            }


}
