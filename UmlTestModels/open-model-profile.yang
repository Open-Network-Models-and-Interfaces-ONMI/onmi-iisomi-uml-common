module open-model-profile {
	namespace "urn:iisomi:params:xml:ns:yang:open-model-profile";
	prefix omp;
	organization "IISOMI";
	contact "none";
	description "none";
	revision 2017-03-14 {
		description "Initial revision";
		reference "ONF-TR-531, RFC 6020 and RFC 6087";
	}

//************************************
//            default-identities
//************************************
	identity open-model-class-id {
		description
			"The identity of the single root for all
			 identities in the model. Note that section
			 7.18.2 in RFC7950 says that identity derivation is
			 irreflexive (i.e., an identity cannot be derived
			 from itself.";
	}
	
	typedef open-model-class-t {
		type identityref {
			base open-model-class-id;
		}
		description "The type of the concrete OpenModelClass";
	}
	
	grouping open-model-class-g {
		leaf entity-class {
			type open-model-class-t;
			description "The base identity reference to hold the entity class name";
		}
		leaf specification-class {
			type open-model-class-t;
			description "The base identity reference to hold the specification class name";
		}
		description "The grouping representing the OpenModelClass meta-data";
	}
}
